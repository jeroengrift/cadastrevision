FME workspace 8_finalStatsOverlapBRKTopo.fmw

Parameters:
- stat_files = D:\PhD\data\raster\analysis_brk_topo_all\classes_stats\tile-20000-370000.gpkg   # "" stat_files
- input_dir = D:\PhD\data\raster\analysis_brk_topo_all

Note: Script that calculates: / - the percentages matched per class / - The percentage matched total / - The percentage not matched total
Creator_3
    GEOMTYPE = Geometry Object
    NUM = 1
    CREATED -> FeatureReader [INITIATOR]
    CREATED -> FeatureReader_3 [INITIATOR]
    CREATED -> FeatureReader_4 [INITIATOR]
FeatureReader [off]
    ATTRIBUTES = classes_stats_tile,"class,filename_10k,brk_length.total_count,brk_length.sum,id"
    ATTR_ACCUM_MODE = Only Use Result
    COMBINE_GEOM = Use Result
    DATASET = $(stat_files)
    FEATURETYPES = classes_stats_tile
    FORMAT = OGCGEOPACKAGE
    INTERACT = NONE
    OGCGEOPACKAGE_ENCODE_FEATURE_TYPE_AND_ATTR_NAMES = YES
    OGCGEOPACKAGE_ENFORCE_FOREIGN_KEY_INTEGRITY = YES
    OGCGEOPACKAGE_EXPOSE_PRIMARY_KEY_ATTRIBUTE = YES
    OGCGEOPACKAGE_OPEN_SINGLE_RASTER_AS_SUBDATASET = YES
    OGCGEOPACKAGE_QUERY_FEATURE_TYPES_FOR_MERGE_FILTERS = Yes
    OGCGEOPACKAGE_READER_REPLACE_INVALID_CHARS = NO
    OGCGEOPACKAGE_READ_BOOLEANS_AS_YES_NO = YES
    OGCGEOPACKAGE_READ_NULLS = YES
    OGCGEOPACKAGE_USE_SEARCH_ENVELOPE = NO
    OUTPUT_FEATURES_DISPLAY = Schema and Data Features
    classes_stats_tile -> StatisticsCalculator [off]
StatisticsCalculator [off]
    ATTR_ACCUM_MODE = None
    CALCULATION_MODE = NUMERIC
    FEAT_STATS = brk_length.sum,NUMERIC_MODE,,,COUNT,SUM,,,,,,,,,;brk_length.total_count,NUMERIC_MODE,,,COUNT,SUM,,,,,,,,,
    GROUP_BY = class
    SUMMARY -> classes_stats [off]
classes_stats: Inspector [off]
FeatureReader_3
    ATTRIBUTES = brk_matched,"path_windows,tile,gpkg_type,path_filename,filename_10k,brk_id,brk_gemeente,brk_gemeente_code,brk_sectie,id,id_0"
    ATTR_ACCUM_MODE = Only Use Result
    COMBINE_GEOM = Use Result
    DATASET = $(input_dir)\brk_matched.gpkg
    FEATURETYPES = brk_matched
    FORMAT = OGCGEOPACKAGE
    GEOMETRY_TYPES = brk_matched,""",fme_arc,fme_area,fme_collection,fme_line,fme_point,fme_solid"""
    INTERACT = NONE
    OGCGEOPACKAGE_ENCODE_FEATURE_TYPE_AND_ATTR_NAMES = YES
    OGCGEOPACKAGE_ENFORCE_FOREIGN_KEY_INTEGRITY = YES
    OGCGEOPACKAGE_EXPOSE_PRIMARY_KEY_ATTRIBUTE = YES
    OGCGEOPACKAGE_OPEN_SINGLE_RASTER_AS_SUBDATASET = YES
    OGCGEOPACKAGE_QUERY_FEATURE_TYPES_FOR_MERGE_FILTERS = Yes
    OGCGEOPACKAGE_READER_REPLACE_INVALID_CHARS = NO
    OGCGEOPACKAGE_READ_BOOLEANS_AS_YES_NO = YES
    OGCGEOPACKAGE_READ_NULLS = YES
    OGCGEOPACKAGE_USE_SEARCH_ENVELOPE = NO
    OUTPUT_FEATURES_DISPLAY = Schema and Data Features
    brk_matched -> Aggregator
Aggregator
    ACCUM_ATTRS_NAME = Drop Incoming Attributes
    AGGREGATE_TYPE = Homogeneous Collection (If Possible)
    GROUP_BY = filename_10k brk_id
    MODE = Geometry - Assemble One Level
    SEP = ,
    AGGREGATE -> LengthCalculator
LengthCalculator
    DIM = 2
    LEN_ATTR = _length
    MULT = 1
    -> StatisticsCalculator_2
StatisticsCalculator_2
    ATTR_ACCUM_MODE = None
    CALCULATION_MODE = NUMERIC
    FEAT_STATS = _length,NUMERIC_MODE,,,,SUM,,,,,,,,,
    SUMMARY -> matched
matched: Inspector
FeatureReader_4
    ATTRIBUTES = brk_unmatched,"path_windows,tile,gpkg_type,path_filename,filename_10k,brk_id,brk_gemeente,brk_gemeente_code,brk_sectie,id,id_0"
    ATTR_ACCUM_MODE = Only Use Result
    COMBINE_GEOM = Use Result
    DATASET = $(input_dir)\brk_unmatched.gpkg
    FEATURETYPES = brk_unmatched
    FORMAT = OGCGEOPACKAGE
    GEOMETRY_TYPES = brk_unmatched,""",fme_arc,fme_area,fme_collection,fme_line,fme_point,fme_solid"""
    INTERACT = NONE
    OGCGEOPACKAGE_ENCODE_FEATURE_TYPE_AND_ATTR_NAMES = YES
    OGCGEOPACKAGE_ENFORCE_FOREIGN_KEY_INTEGRITY = YES
    OGCGEOPACKAGE_EXPOSE_PRIMARY_KEY_ATTRIBUTE = YES
    OGCGEOPACKAGE_OPEN_SINGLE_RASTER_AS_SUBDATASET = YES
    OGCGEOPACKAGE_QUERY_FEATURE_TYPES_FOR_MERGE_FILTERS = Yes
    OGCGEOPACKAGE_READER_REPLACE_INVALID_CHARS = NO
    OGCGEOPACKAGE_READ_BOOLEANS_AS_YES_NO = YES
    OGCGEOPACKAGE_READ_NULLS = YES
    OGCGEOPACKAGE_USE_SEARCH_ENVELOPE = NO
    OUTPUT_FEATURES_DISPLAY = Schema and Data Features
    brk_unmatched -> Aggregator_2
Aggregator_2
    ACCUM_ATTRS_NAME = Drop Incoming Attributes
    AGGREGATE_TYPE = Homogeneous Collection (If Possible)
    GROUP_BY = filename_10k brk_id
    MODE = Geometry - Assemble One Level
    SEP = ,
    AGGREGATE -> LengthCalculator_2
LengthCalculator_2
    DIM = 2
    LEN_ATTR = _length
    MULT = 1
    -> StatisticsCalculator_3
StatisticsCalculator_3
    ATTR_ACCUM_MODE = None
    CALCULATION_MODE = NUMERIC
    FEAT_STATS = _length,NUMERIC_MODE,,,,SUM,,,,,,,,,
    SUMMARY -> unmatched
unmatched: Inspector
