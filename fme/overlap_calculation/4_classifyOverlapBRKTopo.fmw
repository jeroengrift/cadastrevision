FME workspace 4_classifyOverlapBRKTopo.fmw

Parameters:
- filename = tile-20000-370000
- input_dir = D:\PhD\data\raster\analysis_brk_topo_all
- sample_file = D:\PhD\data\benchmark\vector\tiles\sample_tiles_10k_split.gpkg

Note: This script is used to classify the output of script 1 and 2. The output is written to the classes directory in the input folder
Creator
    GEOMTYPE = Geometry Object
    NUM = 1
    CREATED -> FeatureReader_4 [INITIATOR]
FeatureReader_4
    ATTRIBUTES = tiles_copy,"id,landscape,filename_10k,overlap_landscape,overlap_non_urban,overlap_total,shape_leng,split,fid"
    ATTR_ACCUM_MODE = Only Use Result
    COMBINE_GEOM = Use Result
    DATASET = $(sample_file)
    FEATURETYPES = tiles_copy
    FORMAT = OGCGEOPACKAGE
    GEOMETRY_TYPES = tiles_copy,""",fme_area"""
    INTERACT = NONE
    OGCGEOPACKAGE_ENCODE_FEATURE_TYPE_AND_ATTR_NAMES = YES
    OGCGEOPACKAGE_ENFORCE_FOREIGN_KEY_INTEGRITY = YES
    OGCGEOPACKAGE_EXPOSE_PRIMARY_KEY_ATTRIBUTE = YES
    OGCGEOPACKAGE_OPEN_SINGLE_RASTER_AS_SUBDATASET = YES
    OGCGEOPACKAGE_QUERY_FEATURE_TYPES_FOR_MERGE_FILTERS = Yes
    OGCGEOPACKAGE_READER_REPLACE_INVALID_CHARS = NO
    OGCGEOPACKAGE_READ_BOOLEANS_AS_YES_NO = YES
    OGCGEOPACKAGE_READ_NULLS = YES
    OGCGEOPACKAGE_USE_SEARCH_ENVELOPE = NO
    OUTPUT_FEATURES_DISPLAY = Schema and Data Features
    tiles_copy -> StringReplacer
StringReplacer
    CASE = NO
    FIND_TEXT = .tif
    NO_MATCH = _FME_NO_OP_
    REGEXP = NO
    SRC_ATTRS = filename_10k
    -> TestFilter_2
TestFilter_2
    DEFAULT_VALUE = <UNFILTERED>
    PASSED_TEST_GROUP_OUTPUT = FIRST
    TEST_LIST = "BOOL_OP,OR,COMPOSITE_TEST,""""""1"""""",TEST_CLAUSE,TEST @Value(filename_10k) = $(filename)",__Tile_ =
    __Tile_ = -> FeatureReader_3 [INITIATOR]
    __Tile_ = -> FeatureReader [INITIATOR]
FeatureReader_3
    ATTRIBUTES = brk_overlap,"path_windows,tile,gpkg_type,path_filename,overlap,filename_10k,brk_id,brk_area,brk_azimuth,brk_gemeente,brk_gemeente_code,brk_sectie,brk_clip_area,type,topo_id,topo_azimuth,topo_clip_area,topo_source,topo_overlap,id,id_0"
    ATTR_ACCUM_MODE = Only Use Result
    COMBINE_GEOM = Use Result
    DATASET = $(input_dir)\brk_overlap.gpkg
    FEATURETYPES = brk_overlap
    FORMAT = OGCGEOPACKAGE
    GEOMETRY_TYPES = brk_overlap,""",fme_arc,fme_area,fme_collection,fme_line,fme_point,fme_solid"""
    INTERACT = NONE
    OGCGEOPACKAGE_ENCODE_FEATURE_TYPE_AND_ATTR_NAMES = YES
    OGCGEOPACKAGE_ENFORCE_FOREIGN_KEY_INTEGRITY = YES
    OGCGEOPACKAGE_EXPOSE_PRIMARY_KEY_ATTRIBUTE = YES
    OGCGEOPACKAGE_OPEN_SINGLE_RASTER_AS_SUBDATASET = YES
    OGCGEOPACKAGE_QUERY_FEATURE_TYPES_FOR_MERGE_FILTERS = Yes
    OGCGEOPACKAGE_READER_REPLACE_INVALID_CHARS = NO
    OGCGEOPACKAGE_READ_BOOLEANS_AS_YES_NO = YES
    OGCGEOPACKAGE_READ_NULLS = YES
    OGCGEOPACKAGE_USE_SEARCH_ENVELOPE = NO
    OUTPUT_FEATURES_DISPLAY = Schema and Data Features
    WHERE = "filename_10k" = "@Value(filename_10k)"
    brk_overlap -> FeatureMerger [REQUESTOR]
FeatureReader
    ATTRIBUTES = brk_matched,"path_windows,tile,gpkg_type,path_filename,filename_10k,brk_id,brk_gemeente,brk_gemeente_code,brk_sectie,id,id_0"
    ATTR_ACCUM_MODE = Only Use Result
    COMBINE_GEOM = Use Result
    DATASET = $(input_dir)\brk_matched.gpkg
    FEATURETYPES = brk_matched
    FORMAT = OGCGEOPACKAGE
    GEOMETRY_TYPES = brk_matched,""",fme_arc,fme_area,fme_collection,fme_line,fme_point,fme_solid"""
    INTERACT = NONE
    OGCGEOPACKAGE_ENCODE_FEATURE_TYPE_AND_ATTR_NAMES = YES
    OGCGEOPACKAGE_ENFORCE_FOREIGN_KEY_INTEGRITY = YES
    OGCGEOPACKAGE_EXPOSE_PRIMARY_KEY_ATTRIBUTE = YES
    OGCGEOPACKAGE_OPEN_SINGLE_RASTER_AS_SUBDATASET = YES
    OGCGEOPACKAGE_QUERY_FEATURE_TYPES_FOR_MERGE_FILTERS = Yes
    OGCGEOPACKAGE_READER_REPLACE_INVALID_CHARS = NO
    OGCGEOPACKAGE_READ_BOOLEANS_AS_YES_NO = YES
    OGCGEOPACKAGE_READ_NULLS = YES
    OGCGEOPACKAGE_USE_SEARCH_ENVELOPE = NO
    OUTPUT_FEATURES_DISPLAY = Schema and Data Features
    WHERE = "filename_10k" = "@Value(filename_10k)"
    brk_matched -> FeatureMerger [SUPPLIER]
FeatureMerger
    ATTR_ACCUM_MODE = Merge Supplier
    ATTR_CONFLICT_RES = Use Requestor
    CLEANING_TOLERANCE = Automatic
    CONNECT_Z_MODE = First Wins
    GEOM_TYPE = Build Polygons
    IGNORE_NULLS = No
    JOIN_KEYS = @Value(brk_id) @Value(brk_id) AUTO @Value(filename_10k) @Value(filename_10k) AUTO
    MERGE_TYPE = Attributes and Geometry
    PROCESS_DUPS = YES
    REJECT_NULL_MISSING_KEYS = No
    SUPPLIERS_FIRST = No
    MERGED -> LengthCalculator_3
    UNUSED_SUPPLIER -> FeatureMerger_UnusedSupplier
LengthCalculator_3
    DIM = 2
    LEN_ATTR = brk_length
    MULT = 1
    -> TestFilter_3
Note: Merge classes: / - Building / - Built up / - Water / - Road / - Bare / - Vegetation / - Others
TestFilter_3
    DEFAULT_VALUE = <UNFILTERED>
    PASSED_TEST_GROUP_OUTPUT = FIRST
    TEST_LIST:
      "BOOL_OP,OR,COMPOSITE_TEST,""""""1 OR 2 OR 3"""""",TEST_CLAUSE,CASE_INSENSITIVE_TEST @Value(type) CONTAINS pand
      CASE_INSENSITIVE_TEST @Value(type) CONTAINS gebouwvlak
      CASE_INSENSITIVE_TEST @Value(type) CONTAINS overigbouwwerk",@Value(type) = building,"BOOL_OP,OR,COMPOSITE_TEST,""""""1 OR 2 OR 3 OR 4 OR 5 OR 6 OR 7 OR 8 OR 9 OR 10 OR 11 OR 12 OR 13"""""",TEST_CLAUSE,TEST @Value(type) = spoor
      TEST @Value(type) = spoorlijn
      TEST @Value(type) = ondersteunendwegdeel_gesloten verharding
      TEST @Value(type) = ondersteunendwegdeel_half verhard
      TEST @Value(type) = ondersteunendwegdeel_open verharding
      TEST @Value(type) = terrein_spoorbaanlichaam
      TEST @Value(type) = wegdeel_gesloten verharding
      TEST @Value(type) = wegdeel_onverhard
      TEST @Value(type) = wegdeel_half verhard
      TEST @Value(type) = wegdeel_open verharding
      TEST @Value(type) = weghartlijn
      TEST @Value(type) = weglijn
      TEST @Value(type) = wegvlak",@Value(type) = road,"BOOL_OP,OR,COMPOSITE_TEST,""""""1 OR 2 OR 3 OR 4"""""",TEST_CLAUSE,TEST @Value(type) = waterhartlijn
      TEST @Value(type) = waterdeel
      TEST @Value(type) = ondersteunendwaterdeel
      TEST @Value(type) = watervlak",@Value(type) = water,"BOOL_OP,OR,COMPOSITE_TEST,""""""1 OR 2 OR 3 OR 4 OR 5 OR 6 OR 7 OR 8 OR 9 OR 10 OR 11 OR 12 OR 13 OR 14 OR 15 OR 16 OR 17 OR 18 OR 19 OR 20"""""",TEST_CLAUSE,CASE_INSENSITIVE_TEST @Value(type) BEGINS_WITH begroeidterreindeel_
      CASE_INSENSITIVE_TEST @Value(type) BEGINS_WITH gewasperceel_
      TEST @Value(type) = inrichtingselementlijn_bomenrij
      TEST @Value(type) = inrichtingselementlijn_heg, haag
      TEST @Value(type) = ondersteunendwegdeel_groenvoorziening
      TEST @Value(type) = terrein_akkerland
      TEST @Value(type) = terrein_boomgaard
      TEST @Value(type) = terrein_boomkwekerij
      TEST @Value(type) = terrein_bos: gemengd bos
      TEST @Value(type) = terrein_bos: griend
      TEST @Value(type) = terrein_bos: loofbos
      TEST @Value(type) = terrein_bos: naaldbos
      TEST @Value(type) = terrein_braakliggend
      TEST @Value(type) = terrein_dodenakker
      TEST @Value(type) = terrein_duin
      TEST @Value(type) = terrein_fruitkwekerij
      TEST @Value(type) = terrein_grasland
      TEST @Value(type) = terrein_heide
      TEST @Value(type) = terrein_populieren
      TEST @Value(type) = terrein_dodenakker met bos",@Value(type) = vegetation,"BOOL_OP,OR,COMPOSITE_TEST,""""""1 OR 2 OR 3 OR 4 OR 5 OR 6 OR 7 OR 8 OR 9 OR 10 OR 11 OR 12 OR 13 OR 14 OR 15 OR 16 OR 17 OR 18 OR 19 OR 20 OR 21"""""",TEST_CLAUSE,TEST @Value(type) = inrichtingselementlijn_aanlegsteiger
      TEST @Value(type) = inrichtingselementlijn_calamiteitendoorgang
      TEST @Value(type) = inrichtingselementlijn_geluidswering
      TEST @Value(type) = inrichtingselementlijn_hekwerk
      TEST @Value(type) = inrichtingselementlijn_koedam
      TEST @Value(type) = inrichtingselementlijn_muur
      TEST @Value(type) = inrichtingselementlijn_paalwerk
      TEST @Value(type) = inrichtingselementlijn_schietbaan
      TEST @Value(type) = inrichtingselementlijn_sluisdeur
      TEST @Value(type) = inrichtingselementlijn_strekdam, krib, golfbreker
      TEST @Value(type) = inrichtingselementlijn_stuw
      TEST @Value(type) = inrichtingselementlijn_tol
      TEST @Value(type) = inrichtingselementlijn_verkeersgeleider
      TEST @Value(type) = inrichtingselementlijn_wegafsluiting
      TEST @Value(type) = onbegroeidterreindeel_erf
      TEST @Value(type) = onbegroeidterreindeel_gesloten verharding
      TEST @Value(type) = onbegroeidterreindeel_half verhard
      TEST @Value(type) = onbegroeidterreindeel_open verharding
      CASE_INSENSITIVE_TEST @Value(type) BEGINS_WITH scheiding_
      TEST @Value(type) = terrein_aanlegsteiger
      TEST @Value(type) = terrein_bebouwd gebied",@Value(type) = built-up,"BOOL_OP,OR,COMPOSITE_TEST,""""""1 OR 2 OR 3 OR 4 OR 5"""""",TEST_CLAUSE,TEST @Value(type) = terrein_basaltblokken, steenglooiing
      TEST @Value(type) = ondersteunendwegdeel_onverhard
      TEST @Value(type) = onbegroeidterreindeel_zand
      TEST @Value(type) = onbegroeidterreindeel_onverhard
      TEST @Value(type) = terrein_zand",@Value(type) = bare
    @Value(type) = building -> AttributeManager_27
    @Value(type) = road -> AttributeManager_46
    @Value(type) = water -> AttributeManager_47
    @Value(type) = vegetation -> AttributeManager_48
    @Value(type) = built-up -> AttributeManager_8
    @Value(type) = bare -> AttributeManager_51
    <UNFILTERED> -> AttributeManager_49
AttributeManager_27
    ATTR_TABLE = SET_TO class = building
    USER_EXPOSED_ATTRIBUTES = topo_overlap_length,clip_length
    -> AttributeManager_50
AttributeManager_46
    ATTR_TABLE = SET_TO class = road
    USER_EXPOSED_ATTRIBUTES = _length,azimuth_diff,topo_overlap_length,clip_length
    -> AttributeManager_50
AttributeManager_47
    ATTR_TABLE = SET_TO class = water
    USER_EXPOSED_ATTRIBUTES = _length,azimuth_diff,topo_overlap_length,clip_length
    -> AttributeManager_50
AttributeManager_48
    ATTR_TABLE = SET_TO class = vegetation
    USER_EXPOSED_ATTRIBUTES = _length,azimuth_diff,clip_length,topo_overlap_length
    -> AttributeManager_50
AttributeManager_8
    ATTR_TABLE = SET_TO class (buffer) = built-up
    USER_EXPOSED_ATTRIBUTES = azimuth_diff,topo_overlap_length,clip_length
    -> AttributeManager_50
AttributeManager_51
    ATTR_TABLE = SET_TO class = bare
    USER_EXPOSED_ATTRIBUTES = topo_overlap_length,azimuth_diff,clip_length
    -> AttributeManager_50
AttributeManager_49
    ATTR_TABLE = SET_TO class = others
    USER_EXPOSED_ATTRIBUTES = _length,azimuth_diff,topo_overlap_length,clip_length
    -> AttributeManager_50
AttributeManager_50
    ATTR_TABLE:
      REMOVE brk_azimuth
      REMOVE brk_gemeente
      REMOVE brk_gemeente_code
      REMOVE brk_sectie
      REMOVE topo_id
      REMOVE topo_azimuth
      REMOVE brk_length
    USER_EXPOSED_ATTRIBUTES = azimuth_diff,topo_overlap_length,clip_length
    -> FeatureWriter [Output]
FeatureWriter
    DATASET = $(input_dir)\classes\@Value(filename_10k)_class.gpkg
    DATASET_ATTR = _dataset
    FEATURE_TYPE_LIST_ATTR = _feature_types
    FORMAT = OGCGEOPACKAGE
    OGCGEOPACKAGE_COORDINATE_SYSTEM_GRANULARITY = FEATURE_TYPE
    OGCGEOPACKAGE_DESTINATION_DATASETTYPE_VALIDATION = Yes
    OGCGEOPACKAGE_ENCODE_FEATURE_TYPE_AND_ATTR_NAMES = YES
    OGCGEOPACKAGE_ENFORCE_GEOMETRY_COLUMN_CONSTRAINTS = YES
    OGCGEOPACKAGE_EXPOSE_PRIMARY_KEY_ATTRIBUTE = YES
    OGCGEOPACKAGE_OVERWRITE_DATASET = NO
    OGCGEOPACKAGE_TRANSACTION_SIZE = 5000
    OGCGEOPACKAGE_VERSION = 1.2
    OGCGEOPACKAGE_WRITE_NULLS = YES
    TOTAL_FEATURES_WRITTEN_ATTR = _total_features_written
FeatureMerger_UnusedSupplier: Inspector [off]
