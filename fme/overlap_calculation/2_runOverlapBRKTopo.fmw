FME workspace 2_runOverlapBRKTopo.fmw

Creator
    GEOMTYPE = Geometry Object
    NUM = 1
    CREATED -> FeatureReader [INITIATOR]
FeatureReader
    ATTRIBUTES = tiles,"landscape,filename_10k,overlap_landscape,overlap_non_urban,overlap_total,shape_leng,id"
    ATTR_ACCUM_MODE = Only Use Result
    COMBINE_GEOM = Use Result
    DATASET = /media/bitlockermount/PhD/data/vector/sample/sample_tiles_10k.gpkg
    FEATURETYPES = tiles
    FORMAT = OGCGEOPACKAGE
    INTERACT = NONE
    OGCGEOPACKAGE_ENCODE_FEATURE_TYPE_AND_ATTR_NAMES = YES
    OGCGEOPACKAGE_ENFORCE_FOREIGN_KEY_INTEGRITY = YES
    OGCGEOPACKAGE_EXPOSE_PRIMARY_KEY_ATTRIBUTE = YES
    OGCGEOPACKAGE_OPEN_SINGLE_RASTER_AS_SUBDATASET = YES
    OGCGEOPACKAGE_QUERY_FEATURE_TYPES_FOR_MERGE_FILTERS = Yes
    OGCGEOPACKAGE_READER_REPLACE_INVALID_CHARS = YES
    OGCGEOPACKAGE_READ_BOOLEANS_AS_YES_NO = YES
    OGCGEOPACKAGE_READ_NULLS = YES
    OGCGEOPACKAGE_USE_SEARCH_ENVELOPE = NO
    OUTPUT_FEATURES_DISPLAY = Schema and Data Features
    tiles -> WorkspaceRunner
WorkspaceRunner
    BLOCKING = No
    MAX_PROC = 4
    MAX_TO_BATCH = 1
    WORKSPACE_FILE = $(FME_MF_DIR)1_OverlapBRKTopo.fmw
    WORKSPACE_PARAMETERS = buffer,2,Output_dir,/media/bitlockermount/BGT/run_all_data_2_50_02_10,overlap,50,azimuth_threshold,0.2,snipping_length,10,file,@Value(filename_10k)
