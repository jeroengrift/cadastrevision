FME workspace 7_runAnalyseClassesOverlapBRKTopo.fmw

Parameters:
- sample_file = D:\PhD\data\benchmark\vector\tiles\sample_tiles_10k_split.gpkg

Creator_3
    GEOMTYPE = Geometry Object
    NUM = 1
    CREATED -> FeatureReader_2 [INITIATOR]
FeatureReader_2
    ATTRIBUTES = tiles_copy,"id,landscape,filename_10k,overlap_landscape,overlap_non_urban,overlap_total,shape_leng,split,fid"
    ATTR_ACCUM_MODE = Only Use Result
    COMBINE_GEOM = Use Result
    DATASET = $(sample_file)
    FEATURETYPES = tiles_copy
    FORMAT = OGCGEOPACKAGE
    GEOMETRY_TYPES = tiles_copy,""",fme_area"""
    INTERACT = NONE
    OGCGEOPACKAGE_ENCODE_FEATURE_TYPE_AND_ATTR_NAMES = YES
    OGCGEOPACKAGE_ENFORCE_FOREIGN_KEY_INTEGRITY = YES
    OGCGEOPACKAGE_EXPOSE_PRIMARY_KEY_ATTRIBUTE = YES
    OGCGEOPACKAGE_OPEN_SINGLE_RASTER_AS_SUBDATASET = YES
    OGCGEOPACKAGE_QUERY_FEATURE_TYPES_FOR_MERGE_FILTERS = Yes
    OGCGEOPACKAGE_READER_REPLACE_INVALID_CHARS = YES
    OGCGEOPACKAGE_READ_BOOLEANS_AS_YES_NO = YES
    OGCGEOPACKAGE_READ_NULLS = YES
    OGCGEOPACKAGE_USE_SEARCH_ENVELOPE = NO
    OUTPUT_FEATURES_DISPLAY = Schema and Data Features
    tiles_copy -> WorkspaceRunner
WorkspaceRunner
    BLOCKING = No
    MAX_PROC = 2
    MAX_TO_BATCH = 2
    WORKSPACE_FILE = $(FME_MF_DIR)6_analyseClassesOverlapBRKTopo.fmw
    WORKSPACE_PARAMETERS = file,@Value(filename_10k),input_dir,D:\PhD\data\raster\analysis_brk_topo_all,sample_file,D:\PhD\data\vector\sample\sample_tiles_10k_split.gpkg
