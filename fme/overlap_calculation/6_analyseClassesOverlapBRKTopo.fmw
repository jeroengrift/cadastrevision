FME workspace 6_analyseClassesOverlapBRKTopo.fmw

Parameters:
- file = tile-20000-370000.tif
- input_dir = D:\PhD\data\raster\analysis_brk_topo_all
- sample_file = D:\PhD\data\vector\sample\sample_tiles_10k_split.gpkg

Note: This script analysis the classification of the matched erk segments.
Creator_3
    GEOMTYPE = Geometry Object
    NUM = 1
    CREATED -> FeatureReader_2 [INITIATOR]
FeatureReader_2
    ATTRIBUTES = tiles_copy,"id,landscape,filename_10k,overlap_landscape,overlap_non_urban,overlap_total,shape_leng,split,fid"
    ATTR_ACCUM_MODE = Only Use Result
    COMBINE_GEOM = Use Result
    DATASET = $(sample_file)
    FEATURETYPES = tiles_copy
    FORMAT = OGCGEOPACKAGE
    GEOMETRY_TYPES = tiles_copy,""",fme_area"""
    INTERACT = NONE
    OGCGEOPACKAGE_ENCODE_FEATURE_TYPE_AND_ATTR_NAMES = YES
    OGCGEOPACKAGE_ENFORCE_FOREIGN_KEY_INTEGRITY = YES
    OGCGEOPACKAGE_EXPOSE_PRIMARY_KEY_ATTRIBUTE = YES
    OGCGEOPACKAGE_OPEN_SINGLE_RASTER_AS_SUBDATASET = YES
    OGCGEOPACKAGE_QUERY_FEATURE_TYPES_FOR_MERGE_FILTERS = Yes
    OGCGEOPACKAGE_READER_REPLACE_INVALID_CHARS = YES
    OGCGEOPACKAGE_READ_BOOLEANS_AS_YES_NO = YES
    OGCGEOPACKAGE_READ_NULLS = YES
    OGCGEOPACKAGE_USE_SEARCH_ENVELOPE = NO
    OUTPUT_FEATURES_DISPLAY = Schema and Data Features
    tiles_copy -> TestFilter_3
TestFilter_3
    DEFAULT_VALUE = <UNFILTERED>
    PASSED_TEST_GROUP_OUTPUT = FIRST
    TEST_LIST = "BOOL_OP,OR,COMPOSITE_TEST,""""""1"""""",TEST_CLAUSE,TEST @Value(filename_10k) = $(file)",@Value(filename_10k) = __file_
    @Value(filename_10k) = __file_ -> StringReplacer
StringReplacer
    CASE = NO
    FIND_TEXT = .tif
    NO_MATCH = _FME_NO_OP_
    REGEXP = NO
    SRC_ATTRS = filename_10k
    -> FeatureReader [INITIATOR]
FeatureReader
    ATTRIBUTES = classes,"type,class,filename_10k,brk_id,topo_source,path_windows,tile,gpkg_type,path_filename,overlap,brk_area,brk_clip_area,topo_clip_area,topo_overlap,id,id_0,id_1"
    ATTR_ACCUM_MODE = Only Use Result
    COMBINE_GEOM = Use Result
    DATASET = $(input_dir)\classes\@Value(filename_10k)_class.gpkg
    FEATURETYPES = classes
    FORMAT = OGCGEOPACKAGE
    GEOMETRY_TYPES = classes,""",fme_arc,fme_area,fme_collection,fme_line,fme_point,fme_solid"""
    INTERACT = NONE
    OGCGEOPACKAGE_ENCODE_FEATURE_TYPE_AND_ATTR_NAMES = YES
    OGCGEOPACKAGE_ENFORCE_FOREIGN_KEY_INTEGRITY = YES
    OGCGEOPACKAGE_EXPOSE_PRIMARY_KEY_ATTRIBUTE = YES
    OGCGEOPACKAGE_OPEN_SINGLE_RASTER_AS_SUBDATASET = YES
    OGCGEOPACKAGE_QUERY_FEATURE_TYPES_FOR_MERGE_FILTERS = Yes
    OGCGEOPACKAGE_READER_REPLACE_INVALID_CHARS = NO
    OGCGEOPACKAGE_READ_BOOLEANS_AS_YES_NO = YES
    OGCGEOPACKAGE_READ_NULLS = YES
    OGCGEOPACKAGE_USE_SEARCH_ENVELOPE = NO
    OUTPUT_FEATURES_DISPLAY = Schema and Data Features
    classes -> DuplicateFilter_3
DuplicateFilter_3
    INPUT_ORDERED_CHOICE = No
    KEYATTR = brk_id class
    UNIQUE -> AttributeManager_4
AttributeManager_4
    ATTR_TABLE:
      REMOVE id
      REMOVE id_0
    USER_EXPOSED_ATTRIBUTES = clip_length
    -> AttributeManager
AttributeManager
    ATTR_TABLE:
      REMOVE overlap (varchar(200))
      REMOVE brk_area (real64)
      REMOVE brk_clip_area (real64)
      REMOVE topo_clip_area (real64)
      REMOVE topo_overlap (varchar(200))
      REMOVE id_1 (int64)
    -> LengthCalculator
LengthCalculator
    DIM = 2
    LEN_ATTR = brk_length
    MULT = 1
    -> StatisticsCalculator_3
StatisticsCalculator_3
    ATTR_ACCUM_MODE = None
    CALCULATION_MODE = NUMERIC
    FEAT_STATS = brk_length,NUMERIC_MODE,,,COUNT,SUM,,,,,,,,,
    GROUP_BY = filename_10k class
    SUMMARY -> FeatureWriter_2 [Inside]
FeatureWriter_2
    DATASET = $(input_dir)\classes_stats\@Value(filename_10k).gpkg
    DATASET_ATTR = _dataset
    FEATURE_TYPE_LIST_ATTR = _feature_types
    FORMAT = OGCGEOPACKAGE
    OGCGEOPACKAGE_COORDINATE_SYSTEM_GRANULARITY = FEATURE_TYPE
    OGCGEOPACKAGE_DESTINATION_DATASETTYPE_VALIDATION = Yes
    OGCGEOPACKAGE_ENCODE_FEATURE_TYPE_AND_ATTR_NAMES = YES
    OGCGEOPACKAGE_ENFORCE_GEOMETRY_COLUMN_CONSTRAINTS = YES
    OGCGEOPACKAGE_EXPOSE_PRIMARY_KEY_ATTRIBUTE = YES
    OGCGEOPACKAGE_OVERWRITE_DATASET = NO
    OGCGEOPACKAGE_TRANSACTION_SIZE = 5000
    OGCGEOPACKAGE_VERSION = 1.2
    OGCGEOPACKAGE_WRITE_NULLS = YES
    TOTAL_FEATURES_WRITTEN_ATTR = _total_features_written
