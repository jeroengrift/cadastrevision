FME workspace 1_OverlapBRKTopo.fmw

Parameters:
- buffer = 2   # bufffer
- Output_dir = D:\PhD\data\raster   # Output directory
- overlap = 50
- azimuth_threshold = 0.2   # azimuth threshold
- snipping_length = 10   # snipping length
- file = tile-20000-370000.tif
- sample_file = D:\PhD\data\vector\sample\sample_tiles_10k_split.gpkg
- brk_file = D:\PhD\data\vector\BRK_snapshot\BRK_export_202206292359.gpkg
- brt_files = ""D:\PhD\data\vector\BRT\top10nl\top10nl_Gebouw.gpkg" "D:\PhD\data\vector\BRT\top10nl\top10nl_Inrichtingselement.gpkg" "D:\PhD\data\vector\BRT\top10nl\top10nl_Spoorbaandeel.gpkg" "D:\PhD\data\vector\BRT\top10nl\top10nl_Terrein.gpkg" "D:\PhD\data\vector\BRT\top10nl\top10nl_Waterdeel.gpkg" "D:\PhD\data\vector\BRT\top10nl\top10nl_Wegdeel.gpkg""
- bgt_file = D:\PhD\data\vector\BGT\download\merge\bgt_download.gpkg
- brp_file = D:\PhD\data\vector\BRP\brpgewaspercelen_definitief_2021.gpkg
- bag_file = D:\PhD\data\vector\BAG\bag-light.gpkg

Note: This script forms the basis for the overlap analysis between the cadastral borders and the topographic objects. / The following inputs should be set: / 1. Buffer distance / 2. Output directory / 3. Overlap / 4. Azimuth threshold / 5. Snipping length / 6. Filename / 7. Sample tiles file / 8. BRK file / 9. BGT file / 10. BRT file / 11. BRP file / 12. BAG file / After setting these parameters the script performs an overlap analysis and writes the results to the output directory. The following files are created: / 1. brk.gpkg: the brk lines of the processed tile / 2. brk_matched.gpkg: the matched brk segments / 3. brk_overlap.gpkg: coupling table to persist the type of overlap (class, type) / 4. brk_unmatched.gpkg: the brk lines that were not matched / 5. tiles.gpkg: the outline of the sample tile / 6. topo.gpkg: the topographic objects used for the overlap analysis / 7. topo_buffer.gpkg: The buffered topographic objects
Junction_16
    -> FeatureReader_4 [INITIATOR]
    -> FeatureReader_3 [INITIATOR]
    -> FeatureReader_6 [INITIATOR]
    -> FeatureReader_2 [INITIATOR]

Bookmark: Read sample tiles
Creator_3
    GEOMTYPE = Geometry Object
    NUM = 1
    CREATED -> FeatureReader [INITIATOR]
FeatureReader
    ATTRIBUTES = tiles_copy,"id,landscape,filename_10k,overlap_landscape,overlap_non_urban,overlap_total,shape_leng,split,fid"
    ATTR_ACCUM_MODE = Only Use Result
    COMBINE_GEOM = Use Result
    DATASET = $(sample_file)
    FEATURETYPES = tiles_copy
    FORMAT = OGCGEOPACKAGE
    GEOMETRY_TYPES = tiles_copy,""",fme_area"""
    INTERACT = NONE
    OGCGEOPACKAGE_ENCODE_FEATURE_TYPE_AND_ATTR_NAMES = YES
    OGCGEOPACKAGE_ENFORCE_FOREIGN_KEY_INTEGRITY = YES
    OGCGEOPACKAGE_EXPOSE_PRIMARY_KEY_ATTRIBUTE = YES
    OGCGEOPACKAGE_OPEN_SINGLE_RASTER_AS_SUBDATASET = YES
    OGCGEOPACKAGE_QUERY_FEATURE_TYPES_FOR_MERGE_FILTERS = Yes
    OGCGEOPACKAGE_READER_REPLACE_INVALID_CHARS = YES
    OGCGEOPACKAGE_READ_BOOLEANS_AS_YES_NO = YES
    OGCGEOPACKAGE_READ_NULLS = YES
    OGCGEOPACKAGE_USE_SEARCH_ENVELOPE = NO
    OUTPUT_FEATURES_DISPLAY = Schema and Data Features
    tiles_copy -> TestFilter_3
TestFilter_3
    DEFAULT_VALUE = <UNFILTERED>
    PASSED_TEST_GROUP_OUTPUT = FIRST
    TEST_LIST = "BOOL_OP,OR,COMPOSITE_TEST,""""""1"""""",TEST_CLAUSE,TEST @Value(filename_10k) = $(file)",@Value(filename_10k) = __file_
    @Value(filename_10k) = __file_ -> AttributeManager_5
AttributeManager_5
    ATTR_TABLE:
      REMOVE landscape
      REMOVE overlap_landscape
      REMOVE overlap_non_urban
      REMOVE overlap_total
      REMOVE shape_leng
      REMOVE id
    USER_EXPOSED_ATTRIBUTES = _row,_column
    -> StringReplacer
StringReplacer
    CASE = NO
    FIND_TEXT = .tif
    NO_MATCH = _FME_NO_OP_
    REGEXP = NO
    SRC_ATTRS = filename_10k
    -> Junction
    -> Junction_3
    -> Junction_15
    -> FeatureWriter_9 [Inside]
    -> Junction_7
    -> Junction_13
    -> Junction_23
    -> Junction_25
    -> tiles
tiles: Inspector [off]
Junction
    -> Junction_2
Junction_3
    -> Junction_4
Junction_15
    -> Junction_16
Junction_7
    -> Junction_8
Junction_13
    -> Junction_22
Junction_23
    -> Junction_24
Junction_25
    -> Junction_26
FeatureWriter_9
    DATASET = $(Output_dir)\@Value(filename_10k)\tiles.gpkg
    DATASET_ATTR = _dataset
    FEATURE_TYPE_LIST_ATTR = _feature_types
    FORMAT = OGCGEOPACKAGE
    OGCGEOPACKAGE_COORDINATE_SYSTEM_GRANULARITY = FEATURE_TYPE
    OGCGEOPACKAGE_DESTINATION_DATASETTYPE_VALIDATION = Yes
    OGCGEOPACKAGE_ENCODE_FEATURE_TYPE_AND_ATTR_NAMES = YES
    OGCGEOPACKAGE_ENFORCE_GEOMETRY_COLUMN_CONSTRAINTS = YES
    OGCGEOPACKAGE_EXPOSE_PRIMARY_KEY_ATTRIBUTE = YES
    OGCGEOPACKAGE_OVERWRITE_DATASET = NO
    OGCGEOPACKAGE_TRANSACTION_SIZE = 5000
    OGCGEOPACKAGE_WRITE_NULLS = YES
    TOTAL_FEATURES_WRITTEN_ATTR = _total_features_written

Bookmark: Read BRK-perceel
Junction_2
    -> FeatureReader_5 [INITIATOR]
FeatureReader_5
    ATTRIBUTES = BRKP_OWN.BRK_V_DKK_ACT_PERCEEL,"landscape,filename_10k,overlap_landscape,overlap_non_urban,overlap_total,id,PERC_ID,PERC_KADASTRALE_AANDUIDING,PERC_KOBJV_KADASTER_OBJECT_ID,PERC_ROTATIE_HOEK,KGEMV_GEMEENTE_NAAM,PERC_GEMEENTECODE,PERC_SECTIE,PERC_PERCEELNUMMER,PERC_GROOTTE,PERC_SOORT_GROOTTE,PERC_SOORT_GROOTTE_OMS"
    ATTR_ACCUM_MODE = Merge Initiator and Result
    ATTR_CONFLICT_RES = Use Result
    ATTR_IGNORE_NULLS = No
    COMBINE_GEOM = Use Result
    DATASET = $(brk_file)
    FEATURETYPES = BRKP_OWN.BRK_V_DKK_ACT_PERCEEL
    FORMAT = OGCGEOPACKAGE
    GEOMETRY_TYPES = BRKP_OWN.BRK_V_DKK_ACT_PERCEEL,""",fme_arc,fme_area,fme_collection,fme_line,fme_point,fme_solid"""
    INTERACT = ENVELOPE_INTERSECTS
    OGCGEOPACKAGE_ENFORCE_FOREIGN_KEY_INTEGRITY = NO
    OGCGEOPACKAGE_USE_SEARCH_ENVELOPE = NO
    OUTPUT_FEATURES_DISPLAY = Schema and Data Features
    BRKP_OWN.BRK_V_DKK_ACT_PERCEEL -> StringReplacer_2
StringReplacer_2
    CASE = NO
    FIND_TEXT = .tif
    NO_MATCH = _FME_NO_OP_
    REGEXP = NO
    SRC_ATTRS = filename_10k
    -> AttributeManager_4
AttributeManager_4
    ATTR_TABLE:
      REMOVE grenslijn
      REMOVE id
      REMOVE typeGrensCode
      REMOVE typeGrensWaarde
      REMOVE perceelLinksIdentificatieNamespace
      REMOVE perceelLinksIdentificatieLokaalID
      REMOVE perceelRechtsIdentificatieNamespace
      REMOVE perceelRechtsIdentificatieLokaalID
      REMOVE landscape
      REMOVE overlap_landscape
      REMOVE overlap_non_urban
      REMOVE overlap_total
      REMOVE PERC_ID
      REMOVE PERC_KADASTRALE_AANDUIDING
      REMOVE PERC_KOBJV_KADASTER_OBJECT_ID
      REMOVE PERC_ROTATIE_HOEK
      RENAME_SET_VALUE KGEMV_GEMEENTE_NAAM > brk_gemeente
      RENAME_SET_VALUE PERC_GEMEENTECODE > brk_gemeente_code
      RENAME_SET_VALUE PERC_SECTIE > brk_sectie
      REMOVE PERC_PERCEELNUMMER
      REMOVE PERC_GROOTTE
      REMOVE PERC_SOORT_GROOTTE
      REMOVE PERC_SOORT_GROOTTE_OMS
    USER_EXPOSED_ATTRIBUTES = y,naam,_predicate,_related_suppliers,_creation_instance
    -> Chopper_4
Chopper_4
    DEAGGREGATE_INPUT = Deaggregate
    MAX_VERTICES = 2
    MODE = By Vertex
    CHOPPED -> GeometryValidator_5
    UNTOUCHED -> GeometryValidator_5
GeometryValidator_5
    PRESETS = All
    REPAIR = Yes
    RULES = AREA_ORIENTATION AREA_ORIENTATION]VALID]FME_CONTROLLER_QUERY_FILE]transformers/dependencies/geometryvalidator8/AREA_ORIENTATION.fme]FME_CONTROLLER_CHOICE]AREA_ORIENTATION CONSECUTIVE_IDENTICAL_VERTICES_2D CHECK_Z]YES]TOLERANCE]0.0]FME_CONTROLLER_QUERY_FILE]transformers/dependencies/geometryvalidator8/CONSECUTIVE_IDENTICAL_VERTICES_2D.fme]FME_CONTROLLER_CHOICE]CONSECUTIVE_IDENTICAL_VERTICES_2D MISSING_TEXTURE_COORDINATES FME_CONTROLLER_QUERY_FILE]transformers/dependencies/geometryvalidator8/MISSING_TEXTURE_COORDINATES.fme]FME_CONTROLLER_CHOICE]MISSING_TEXTURE_COORDINATES MISSING_VERTEX_NORMALS FME_CONTROLLER_QUERY_FILE]transformers/dependencies/geometryvalidator8/MISSING_VERTEX_NORMALS.fme]FME_CONTROLLER_CHOICE]MISSING_VERTEX_NORMALS NAN_REMOVAL PROCESS_MEASURE]NO]FME_CONTROLLER_QUERY_FILE]transformers/dependencies/geometryvalidator8/NAN_REMOVAL.fme]FME_CONTROLLER_CHOICE]NAN_REMOVAL NULL_REMOVAL FME_CONTROLLER_QUERY_FILE]transformers/dependencies/geometryvalidator8/NULL_REMOVAL.fme]FME_CONTROLLER_CHOICE]NULL_REMOVAL OGC_SIMPLE_CHECK LEGACY_OGC]No]FME_CONTROLLER_QUERY_FILE]transformers/dependencies/geometryvalidator8/OGC_SIMPLE_CHECK.fme]FME_CONTROLLER_CHOICE]OGC_SIMPLE_CHECK OGC_VALID_CHECK OGC_VERSION]V1.2.0]LEGACY_OGC]No]FME_CONTROLLER_QUERY_FILE]transformers/dependencies/geometryvalidator8/OGC_VALID_CHECK.fme]FME_CONTROLLER_CHOICE]OGC_VALID_CHECK PLANAR_SURFACE CHECK_AREA]DO_NOT_CHECK_AREA]TOLERANCE_MODE]AUTO]TOLERANCE]<Unused>]ANGULAR_TOLERANCE_MODE]AUTO]ANGULAR_TOLERANCE]<Unused>]FME_CONTROLLER_QUERY_FILE]transformers/dependencies/geometryvalidator8/PLANAR_SURFACE.fme]FME_CONTROLLER_CHOICE]PLANAR_SURFACE SELF_INTERSECTING CHECK_HOLE_TOUCHING_POLYGON]No]CONNECT_Z_MODE_SI]FIRST_WINS]SELF_INTERSECTION_TOLERANCE]None]INTERSECT_ACROSS_MULTIS]No]FME_CONTROLLER_QUERY_FILE]transformers/dependencies/geometryvalidator8/SELF_INTERSECTING.fme]FME_CONTROLLER_CHOICE]SELF_INTERSECTING SHELL_VALIDATION FLIP_APPEARANCE_MODE]FLIP_APPEARANCES]FME_CONTROLLER_QUERY_FILE]transformers/dependencies/geometryvalidator8/SHELL_VALIDATION.fme]FME_CONTROLLER_CHOICE]SHELL_VALIDATION SOLID_VOID_REPAIR FME_CONTROLLER_QUERY_FILE]transformers/dependencies/geometryvalidator8/SOLID_VOID_REPAIR.fme]FME_CONTROLLER_CHOICE]SOLID_VOID_REPAIR TYPE_REPAIR CONNECT_Z_MODE]FIRST_WINS]ARC_ENDPOINT_TOLERANCE_MODE]Auto]ARC_ENDPOINT_TOLERANCE]<Unused>]FME_CONTROLLER_QUERY_FILE]transformers/dependencies/geometryvalidator8/TYPE_REPAIR.fme]FME_CONTROLLER_CHOICE]TYPE_REPAIR MISMATCHED_DIMENSIONS FORCE_DIMENSION]2D]MISMATCHED_Z_VAL]<Unused>]FME_CONTROLLER_QUERY_FILE]transformers/dependencies/geometryvalidator8/MISMATCHED_DIMENSIONS.fme]FME_CONTROLLER_CHOICE]MISMATCHED_DIMENSIONS MISSING_MEASURES_AND_ELEVATIONS MISSING_VALUES_MODE]SENTINEL]MISSING_MEASURES_MODE]<Unused>]SENTINEL_VALUE]0]LENGTH_DIMENSION]<Unused>]FME_CONTROLLER_QUERY_FILE]transformers/dependencies/geometryvalidator8/MISSING_MEASURES_AND_ELEVATIONS.fme]FME_CONTROLLER_CHOICE]MISSING_MEASURES_AND_ELEVATIONS SURFACE_ORIENTATION FME_CONTROLLER_QUERY_FILE]transformers/dependencies/geometryvalidator8/SURFACE_ORIENTATION.fme]FME_CONTROLLER_CHOICE]SURFACE_ORIENTATION SOLID_ORIENTATION FME_CONTROLLER_QUERY_FILE]transformers/dependencies/geometryvalidator8/SOLID_ORIENTATION.fme]FME_CONTROLLER_CHOICE]SOLID_ORIENTATION
    SUMMARY = Detailed
    PASSED -> LineOnLineOverlayer_3 [LINE]
    REPAIRED -> LineOnLineOverlayer_3 [LINE]
LineOnLineOverlayer_3
    ATTRS_ACCUM_MODE = Use Attributes From One Feature
    CLEANING_TOLERANCE = Automatic
    DEAGGREGATE_INPUT = Yes
    GENERATE_LIST_DROP = NO
    GROUP_BY = filename_10k
    SEPARATE_COLLINEAR_SEGMENTS = No
    LINE -> IterativeSnipper_2
IterativeSnipper_2
    DOMAIN = snip__
    SNIPMODE = ToLength
    SnipLength = $(snipping_length)
    -> Clipper_6 [CANDIDATE]
Junction_4
    -> Clipper_6 [CLIPPER]
Clipper_6
    ATTR_ACCUM_MODE = MERGE
    ATTR_CONFLICT_RES = CANDIDATE
    BOUNDARY_CASES = INSIDE
    CLEANING_TOLERANCE = Automatic
    CLIPPERS_FIRST = NO
    GENERATE_LIST = NO
    GROUP_BY = filename_10k
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> CoordinateExtractor_2
CoordinateExtractor_2
    LIST_NAME = _indices
    MODE = All Coordinates
    -> AttributeManager_20
AttributeManager_20
    ATTR_TABLE:
      SET_TO x0 = @Value(_indices{0}.x)
      SET_TO y0 = @Value(_indices{0}.y)
      SET_TO x1 = @Value(_indices{1}.x)
      SET_TO y1 = @Value(_indices{1}.y)
      REMOVE _indices{}.x
      REMOVE _indices{}.y
      REMOVE _indices{}.z
      REMOVE SegmentNumber
      REMOVE shape_leng
    -> AttributeManager_18
Note: Calculate azimuth
AttributeManager_18
    ATTR_TABLE = SET_TO Azimuth = @Evaluate(@atan2((@Value(x1)-@Value(x0)),(@Value(y1)-@Value(y0))))
    -> AttributeManager_21
Note: Correct pi
AttributeManager_21
    ATTR_TABLE:
      SET_TO Azimuth = FME_CONDITIONAL:DEFAULT_VALUE'@Value(Azimuth)'BOOL_OP;OR;COMPOSITE_TEST;<Unused>;TEST @Value(Azimuth) > @Evaluate(@pi())'@Evaluate(@Value(Azimuth)-@pi())'BOOL_OP;AND;COMPOSITE_TEST;<Unused>;TEST @Value(Azimuth) < 0;TEST @Value(Azimuth) > @Evaluate(-@pi())'@Evaluate(@Value(Azimuth)+@pi())'BOOL_OP;AND;COMPOSITE_TEST;<Unused>;TEST @Value(Azimuth) < @Evaluate(-@pi());TEST @Value(Azimuth) > @Evaluate(-(2*@pi()))'@Evaluate(@Value(Azimuth)+(2*@pi()))'FME_NUM_CONDITIONS4___
      REMOVE x0
      REMOVE y0
      REMOVE x1
      REMOVE y1
    -> AttributeManager_22
AttributeManager_22
    ATTR_TABLE = RENAME_SET_VALUE Azimuth > brk_azimuth
    USER_EXPOSED_ATTRIBUTES = filename_1k,PERC_GEMEENTECODE,PERC_SECTIE
    -> Counter
Counter
    CNT_ATTR = brk_id
    SCOPE = Local
    START = 1
    -> LengthCalculator
    -> AttributeManager_17
LengthCalculator
    DIM = 2
    LEN_ATTR = _length
    MULT = 1
    -> AttributeManager_10
AttributeManager_10
    ATTR_TABLE = RENAME_SET_VALUE _length > brk_length
    -> Junction_9
    -> FeatureWriter [Inside]
    -> BRK
Junction_9
    -> Junction_10
FeatureWriter
    DATASET = $(Output_dir)\@Value(filename_10k)\brk.gpkg
    DATASET_ATTR = _dataset
    FEATURE_TYPE_LIST_ATTR = _feature_types
    FORMAT = OGCGEOPACKAGE
    OGCGEOPACKAGE_COORDINATE_SYSTEM_GRANULARITY = FEATURE_TYPE
    OGCGEOPACKAGE_DESTINATION_DATASETTYPE_VALIDATION = Yes
    OGCGEOPACKAGE_ENCODE_FEATURE_TYPE_AND_ATTR_NAMES = YES
    OGCGEOPACKAGE_ENFORCE_GEOMETRY_COLUMN_CONSTRAINTS = YES
    OGCGEOPACKAGE_EXPOSE_PRIMARY_KEY_ATTRIBUTE = YES
    OGCGEOPACKAGE_OVERWRITE_DATASET = NO
    OGCGEOPACKAGE_TRANSACTION_SIZE = 5000
    OGCGEOPACKAGE_WRITE_NULLS = YES
    TOTAL_FEATURES_WRITTEN_ATTR = _total_features_written
BRK: Inspector [off]
AttributeManager_17
    ATTR_TABLE = REMOVE brk_azimuth
    USER_EXPOSED_ATTRIBUTES = filename_1k,count_id,azimuth_brk,KGEMV_GEMEENTE_NAAM,PERC_GEMEENTECODE,PERC_SECTIE
    -> Aggregator_2
    -> FeatureMerger_2 [REQUESTOR]
Aggregator_2
    ACCUM_ATTRS_NAME = Use Attributes From One Feature
    AGGREGATE_TYPE = Homogeneous Collection (If Possible)
    GROUP_BY = filename_10k
    MODE = Geometry - Assemble One Level
    SEP = ,
    AGGREGATE -> LengthCalculator_2
LengthCalculator_2
    DIM = 2
    LEN_ATTR = brk_length
    MULT = 1
    -> GeometryRemover
GeometryRemover
    REMOVE_COORDSYS = No
    -> AttributeManager_27
AttributeManager_27
    USER_EXPOSED_ATTRIBUTES = filename_1k,count_id,azimuth_brk
    -> Junction_11
Junction_11

Bookmark: Process Topo
Junction_10
    -> Clipper [CANDIDATE]
    -> SpatialFilter [Filter]
Junction_18
    -> AttributeManager_35
Junction_20
    -> AttributeManager_35
Junction_21
    -> AttributeManager_35
AttributeManager_35
    USER_EXPOSED_ATTRIBUTES = source,tile
    -> CoordinateExtractor_3
CoordinateExtractor_3
    LIST_NAME = _indices
    MODE = All Coordinates
    -> AttributeManager_24
AttributeManager_24
    ATTR_TABLE:
      SET_TO x0 = @Value(_indices{0}.x)
      SET_TO y0 = @Value(_indices{0}.y)
      SET_TO x1 = @Value(_indices{1}.x)
      SET_TO y1 = @Value(_indices{1}.y)
      REMOVE _indices{}.x
      REMOVE _indices{}.y
      REMOVE _indices{}.z
      REMOVE landscape
      REMOVE overlap_landscape
      REMOVE overlap_non_urban
      REMOVE overlap_total
    -> AttributeManager_14
Note: Calculate azimuth
AttributeManager_14
    ATTR_TABLE = SET_TO Azimuth = @Evaluate(@atan2((@Value(x1)-@Value(x0)),(@Value(y1)-@Value(y0))))
    -> AttributeManager_25
Note: Correct pi
AttributeManager_25
    ATTR_TABLE:
      SET_TO Azimuth = FME_CONDITIONAL:DEFAULT_VALUE'@Value(Azimuth)'BOOL_OP;OR;COMPOSITE_TEST;<Unused>;TEST @Value(Azimuth) > @Evaluate(@pi())'@Evaluate(@Value(Azimuth)-@pi())'BOOL_OP;AND;COMPOSITE_TEST;<Unused>;TEST @Value(Azimuth) < 0;TEST @Value(Azimuth) > @Evaluate(-@pi())'@Evaluate(@Value(Azimuth)+@pi())'BOOL_OP;AND;COMPOSITE_TEST;<Unused>;TEST @Value(Azimuth) < @Evaluate(-@pi());TEST @Value(Azimuth) > @Evaluate(-(2*@pi()))'@Evaluate(@Value(Azimuth)+(2*@pi()))'FME_NUM_CONDITIONS4___
      REMOVE x0
      REMOVE y0
      REMOVE x1
      REMOVE y1
    -> AttributeManager_26
AttributeManager_26
    ATTR_TABLE = RENAME_SET_VALUE Azimuth > topo_azimuth
    USER_EXPOSED_ATTRIBUTES = id,source
    -> Bufferer_3
    -> Alle_topo
    -> FeatureWriter_4 [Inside]
Bufferer_3
    ANGLE = 22.5
    CAP_STYLE = Round
    CORNER_STYLE = Round
    MODE = AREA
    OFFSET = $(buffer)
    OFFSET_UNITS = NONE
    PRECISION = APPROX
    BUFFERED -> Topo_Buffer
    BUFFERED -> FeatureWriter_5 [Inside]
    BUFFERED -> SpatialFilter [Candidate]
SpatialFilter
    AGGREGATE_HANDLING = Yes
    BASE_TYPE = Multiple Filters
    CURVE_BOUNDARY_RULE_PARAM = Default Rule
    PASS_CRITERIA = Pass Against One Filter
    PREDICATES = INTERSECTS
    USE_BOUNDING_BOX = No
    PASSED -> Clipper [CLIPPER]
Clipper
    ATTR_ACCUM_MODE = MERGE
    ATTR_CONFLICT_RES = CANDIDATE
    BOUNDARY_CASES = INSIDE
    CLEANING_TOLERANCE = Automatic
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_ORIGINAL
    PRESERVE_RASTER_EXTENTS = NO
    RASTER_CELL_MODE = CENTER
    Z_VAL_SOURCE = CANDIDATE
    INSIDE -> LengthCalculator_3
FeatureWriter_5
    DATASET = $(Output_dir)\@Value(filename_10k)\topo_buffer.gpkg
    DATASET_ATTR = _dataset
    FEATURE_TYPE_LIST_ATTR = _feature_types
    FORMAT = OGCGEOPACKAGE
    OGCGEOPACKAGE_COORDINATE_SYSTEM_GRANULARITY = FEATURE_TYPE
    OGCGEOPACKAGE_DESTINATION_DATASETTYPE_VALIDATION = Yes
    OGCGEOPACKAGE_ENCODE_FEATURE_TYPE_AND_ATTR_NAMES = YES
    OGCGEOPACKAGE_ENFORCE_GEOMETRY_COLUMN_CONSTRAINTS = YES
    OGCGEOPACKAGE_EXPOSE_PRIMARY_KEY_ATTRIBUTE = YES
    OGCGEOPACKAGE_OVERWRITE_DATASET = NO
    OGCGEOPACKAGE_TRANSACTION_SIZE = 5000
    OGCGEOPACKAGE_WRITE_NULLS = YES
    TOTAL_FEATURES_WRITTEN_ATTR = _total_features_written
Topo_Buffer: Inspector [off]
FeatureWriter_4
    DATASET = $(Output_dir)\@Value(filename_10k)\topo.gpkg
    DATASET_ATTR = _dataset
    FEATURE_TYPE_LIST_ATTR = _feature_types
    FORMAT = OGCGEOPACKAGE
    OGCGEOPACKAGE_COORDINATE_SYSTEM_GRANULARITY = FEATURE_TYPE
    OGCGEOPACKAGE_DESTINATION_DATASETTYPE_VALIDATION = Yes
    OGCGEOPACKAGE_ENCODE_FEATURE_TYPE_AND_ATTR_NAMES = YES
    OGCGEOPACKAGE_ENFORCE_GEOMETRY_COLUMN_CONSTRAINTS = YES
    OGCGEOPACKAGE_EXPOSE_PRIMARY_KEY_ATTRIBUTE = YES
    OGCGEOPACKAGE_OVERWRITE_DATASET = NO
    OGCGEOPACKAGE_TRANSACTION_SIZE = 5000
    OGCGEOPACKAGE_WRITE_NULLS = YES
    TOTAL_FEATURES_WRITTEN_ATTR = _total_features_written
Alle_topo: Inspector [off]

Bookmark: Read BRT
FeatureReader_2
    ATTRIBUTES = top10nl_gebouw_punt,"namespace,lokaalid,brontype,bronactualiteit,bronbeschrijving,bronnauwkeurigheid,mutatietype,typegebouw,fysiekvoorkomen,hoogteklasse,hoogteniveau,hoogte,status,soortnaam,naam,gebruiksdoel,objectbegintijd,tijdstipregistratie,visualisatiecode,tdncode,id,fme_basename",top10nl_gebouw_vlak,"namespace,lokaalid,brontype,bronactualiteit,bronbeschrijving,bronnauwkeurigheid,mutatietype,typegebouw,fysiekvoorkomen,hoogteklasse,hoogteniveau,hoogte,status,soortnaam,naam,gebruiksdoel,objectbegintijd,tijdstipregistratie,visualisatiecode,tdncode,id,fme_basename",top10nl_inrichtingselement_lijn,"namespace,lokaalid,brontype,bronactualiteit,bronbeschrijving,bronnauwkeurigheid,mutatietype,typeinrichtingselement,hoogteniveau,hoogte,nummer,breedte,soortnaam,naam,objectbegintijd,tijdstipregistratie,visualisatiecode,tdncode,id,fme_basename",top10nl_inrichtingselement_punt,"namespace,lokaalid,brontype,bronactualiteit,bronbeschrijving,bronnauwkeurigheid,mutatietype,typeinrichtingselement,hoogteniveau,hoogte,nummer,breedte,soortnaam,naam,objectbegintijd,tijdstipregistratie,visualisatiecode,tdncode,id,fme_basename",top10nl_spoorbaandeel_lijn,"namespace,lokaalid,brontype,bronactualiteit,bronbeschrijving,bronnauwkeurigheid,mutatietype,spoorbreedte,aantalsporen,vervoerfunctie,elektrificatie,brugnaam,tunnelnaam,baanvaknaam,typespoorbaan,hoofdspoor,hoogteniveau,typeinfrastructuur,fysiekvoorkomen,status,objectbegintijd,tijdstipregistratie,visualisatiecode,tdncode,id,fme_basename",top10nl_spoorbaandeel_punt,"namespace,lokaalid,brontype,bronactualiteit,bronbeschrijving,bronnauwkeurigheid,mutatietype,spoorbreedte,aantalsporen,vervoerfunctie,elektrificatie,brugnaam,tunnelnaam,baanvaknaam,typespoorbaan,hoofdspoor,hoogteniveau,typeinfrastructuur,fysiekvoorkomen,status,objectbegintijd,tijdstipregistratie,visualisatiecode,tdncode,id,fme_basename",top10nl_terrein_vlak,"namespace,lokaalid,brontype,bronactualiteit,bronbeschrijving,bronnauwkeurigheid,mutatietype,typelandgebruik,fysiekvoorkomen,voorkomen,hoogteniveau,naam,objectbegintijd,tijdstipregistratie,visualisatiecode,tdncode,id,fme_basename",top10nl_waterdeel_lijn,"namespace,lokaalid,brontype,bronactualiteit,bronbeschrijving,bronnauwkeurigheid,mutatietype,typewater,breedteklasse,hoofdafwatering,fysiekvoorkomen,voorkomen,hoogteniveau,functie,getijdeinvloed,vaarwegklasse,naamofficieel,naamnl,naamfries,isbagnaam,sluisnaam,brugnaam,objectbegintijd,tijdstipregistratie,visualisatiecode,tdncode,id,fme_basename",top10nl_waterdeel_punt,"namespace,lokaalid,brontype,bronactualiteit,bronbeschrijving,bronnauwkeurigheid,mutatietype,typewater,breedteklasse,hoofdafwatering,fysiekvoorkomen,voorkomen,hoogteniveau,functie,getijdeinvloed,vaarwegklasse,naamofficieel,naamnl,naamfries,isbagnaam,sluisnaam,brugnaam,objectbegintijd,tijdstipregistratie,visualisatiecode,tdncode,id,fme_basename",top10nl_waterdeel_vlak,"namespace,lokaalid,brontype,bronactualiteit,bronbeschrijving,bronnauwkeurigheid,mutatietype,typewater,breedteklasse,hoofdafwatering,fysiekvoorkomen,voorkomen,hoogteniveau,functie,getijdeinvloed,vaarwegklasse,naamofficieel,naamnl,naamfries,isbagnaam,sluisnaam,brugnaam,objectbegintijd,tijdstipregistratie,visualisatiecode,tdncode,id,fme_basename",top10nl_wegdeel_hartlijn,"namespace,lokaalid,brontype,bronactualiteit,bronbeschrijving,bronnauwkeurigheid,mutatietype,typeweg,hoogteniveau,typeinfrastructuur,hoofdverkeersgebruik,fysiekvoorkomen,verhardingsbreedteklasse,gescheidenrijbaan,verhardingstype,aantalrijstroken,status,awegnummer,nwegnummer,ewegnummer,swegnummer,afritnummer,afritnaam,isbagnaam,naam,knooppuntnaam,brugnaam,tunnelnaam,objectbegintijd,tijdstipregistratie,visualisatiecode,tdncode,id,fme_basename",top10nl_wegdeel_hartpunt,"namespace,lokaalid,brontype,bronactualiteit,bronbeschrijving,bronnauwkeurigheid,mutatietype,typeweg,hoogteniveau,typeinfrastructuur,hoofdverkeersgebruik,fysiekvoorkomen,verhardingsbreedteklasse,gescheidenrijbaan,verhardingstype,aantalrijstroken,status,awegnummer,nwegnummer,ewegnummer,swegnummer,afritnummer,afritnaam,isbagnaam,naam,knooppuntnaam,brugnaam,tunnelnaam,objectbegintijd,tijdstipregistratie,visualisatiecode,tdncode,id,fme_basename",top10nl_wegdeel_lijn,"namespace,lokaalid,brontype,bronactualiteit,bronbeschrijving,bronnauwkeurigheid,mutatietype,typeweg,hoogteniveau,typeinfrastructuur,hoofdverkeersgebruik,fysiekvoorkomen,verhardingsbreedteklasse,verhardingstype,status,isbagnaam,naam,brugnaam,tunnelnaam,objectbegintijd,tijdstipregistratie,visualisatiecode,tdncode,id,fme_basename",top10nl_wegdeel_punt,"namespace,lokaalid,brontype,bronactualiteit,bronbeschrijving,bronnauwkeurigheid,mutatietype,typeweg,hoogteniveau,typeinfrastructuur,hoofdverkeersgebruik,fysiekvoorkomen,verhardingsbreedteklasse,verhardingstype,status,isbagnaam,naam,brugnaam,tunnelnaam,objectbegintijd,tijdstipregistratie,visualisatiecode,tdncode,id,fme_basename",top10nl_wegdeel_vlak,"namespace,lokaalid,brontype,bronactualiteit,bronbeschrijving,bronnauwkeurigheid,mutatietype,typeweg,hoogteniveau,typeinfrastructuur,hoofdverkeersgebruik,fysiekvoorkomen,verhardingsbreedteklasse,gescheidenrijbaan,verhardingstype,aantalrijstroken,status,awegnummer,nwegnummer,ewegnummer,swegnummer,afritnummer,afritnaam,isbagnaam,naam,knooppuntnaam,brugnaam,tunnelnaam,objectbegintijd,tijdstipregistratie,visualisatiecode,tdncode,id,fme_basename"
    ATTR_ACCUM_MODE = Merge Initiator and Result
    ATTR_CONFLICT_RES = Use Result
    ATTR_IGNORE_NULLS = No
    COMBINE_GEOM = Use Result
    DATASET = $(brt_files)
    FEATURETYPES = top10nl_gebouw_vlak top10nl_inrichtingselement_lijn top10nl_spoorbaandeel_lijn top10nl_terrein_vlak top10nl_waterdeel_lijn top10nl_waterdeel_vlak top10nl_wegdeel_hartlijn top10nl_wegdeel_lijn top10nl_wegdeel_vlak
    FORMAT = OGCGEOPACKAGE
    GEOMETRY_TYPES = top10nl_gebouw_punt,""",fme_point""",top10nl_gebouw_vlak,""",fme_area""",top10nl_inrichtingselement_lijn,""",fme_line""",top10nl_inrichtingselement_punt,""",fme_point""",top10nl_spoorbaandeel_lijn,""",fme_line""",top10nl_spoorbaandeel_punt,""",fme_point""",top10nl_terrein_vlak,""",fme_area""",top10nl_waterdeel_lijn,""",fme_line""",top10nl_waterdeel_punt,""",fme_point""",top10nl_waterdeel_vlak,""",fme_area""",top10nl_wegdeel_hartlijn,""",fme_line""",top10nl_wegdeel_hartpunt,""",fme_point""",top10nl_wegdeel_lijn,""",fme_line""",top10nl_wegdeel_punt,""",fme_point""",top10nl_wegdeel_vlak,""",fme_area"""
    INTERACT = INTERSECTS
    OGCGEOPACKAGE_ENCODE_FEATURE_TYPE_AND_ATTR_NAMES = YES
    OGCGEOPACKAGE_ENFORCE_FOREIGN_KEY_INTEGRITY = YES
    OGCGEOPACKAGE_EXPOSE_PRIMARY_KEY_ATTRIBUTE = YES
    OGCGEOPACKAGE_OGCGEOPACKAGE_EXPOSE_FORMAT_ATTRS = fme_basename,text(50)
    OGCGEOPACKAGE_OPEN_SINGLE_RASTER_AS_SUBDATASET = YES
    OGCGEOPACKAGE_QUERY_FEATURE_TYPES_FOR_MERGE_FILTERS = Yes
    OGCGEOPACKAGE_READER_REPLACE_INVALID_CHARS = YES
    OGCGEOPACKAGE_READ_BOOLEANS_AS_YES_NO = YES
    OGCGEOPACKAGE_READ_NULLS = YES
    OGCGEOPACKAGE_USE_SEARCH_ENVELOPE = NO
    OUTPUT_FEATURES_DISPLAY = Schema and Data Features
    top10nl_gebouw_vlak -> TestFilter_14
    top10nl_inrichtingselement_lijn -> TestFilter
    top10nl_spoorbaandeel_lijn -> TestFilter_10
    top10nl_terrein_vlak -> TestFilter_13
    top10nl_waterdeel_lijn -> TestFilter_12
    top10nl_waterdeel_vlak -> TestFilter_11
    top10nl_wegdeel_hartlijn -> TestFilter_7
    top10nl_wegdeel_lijn -> TestFilter_6
    top10nl_wegdeel_vlak -> TestFilter_9
TestFilter_10
    DEFAULT_VALUE = <UNFILTERED>
    PASSED_TEST_GROUP_OUTPUT = FIRST
    TEST_LIST:
      "BOOL_OP,OR,COMPOSITE_TEST,""""""1 OR 2 OR 3"""""",TEST_CLAUSE,TEST @Value(fysiekvoorkomen) = op vast deel van brug
      TEST @Value(fysiekvoorkomen) = op beweegbaar deel van brug
      TEST @Value(fysiekvoorkomen) = in tunnel",@Value(fysiekvoorkomen) = op vast deel van brug
    <UNFILTERED> -> AttributeManager_23
AttributeManager_23
    ATTR_TABLE:
      REMOVE namespace
      REMOVE lokaalid
      REMOVE brontype
      REMOVE bronactualiteit
      REMOVE bronbeschrijving
      REMOVE bronnauwkeurigheid
      REMOVE mutatietype
      REMOVE spoorbreedte
      REMOVE aantalsporen
      REMOVE vervoerfunctie
      REMOVE elektrificatie
      REMOVE brugnaam
      REMOVE tunnelnaam
      REMOVE baanvaknaam
      REMOVE typespoorbaan
      REMOVE hoofdspoor
      REMOVE hoogteniveau
      REMOVE typeinfrastructuur
      REMOVE fysiekvoorkomen
      REMOVE status
      REMOVE objectbegintijd
      REMOVE tijdstipregistratie
      REMOVE visualisatiecode
      REMOVE tdncode
      REMOVE id
      SET_TO type = spoorlijn
    -> AttributeManager_31
TestFilter_14
    DEFAULT_VALUE = <UNFILTERED>
    PASSED_TEST_GROUP_OUTPUT = FIRST
    TEST_LIST = "BOOL_OP,OR,COMPOSITE_TEST,""""""1"""""",TEST_CLAUSE,TEST @Value(fysiekvoorkomen) = ondergronds",@Value(fysiekvoorkomen) = ondergronds
    <UNFILTERED> -> AttributeManager_30
AttributeManager_30
    ATTR_TABLE:
      REMOVE namespace
      REMOVE lokaalid
      REMOVE brontype
      REMOVE bronactualiteit
      REMOVE bronbeschrijving
      REMOVE bronnauwkeurigheid
      REMOVE mutatietype
      REMOVE fysiekvoorkomen
      REMOVE hoogteklasse
      REMOVE hoogteniveau
      REMOVE hoogte
      REMOVE status
      REMOVE soortnaam
      REMOVE naam
      REMOVE gebruiksdoel
      REMOVE objectbegintijd
      REMOVE tijdstipregistratie
      REMOVE visualisatiecode
      REMOVE tdncode
      REMOVE id
      SET_TO type = gebouwvlak_@Value(typegebouw)
    -> AttributeManager_31
TestFilter
    DEFAULT_VALUE = <UNFILTERED>
    PASSED_TEST_GROUP_OUTPUT = FIRST
    TEST_LIST:
      "BOOL_OP,OR,COMPOSITE_TEST,""""""1 OR 2"""""",TEST_CLAUSE,TEST @Value(typeinrichtingselement) = hoogspanningsleiding
      TEST @Value(typeinrichtingselement) = kabelbaan",@Value(typeinrichtingselement) = hoogspanningsleiding
    <UNFILTERED> -> AttributeManager_29
AttributeManager_29
    ATTR_TABLE:
      REMOVE namespace
      REMOVE lokaalid
      REMOVE brontype
      REMOVE bronactualiteit
      REMOVE bronbeschrijving
      REMOVE bronnauwkeurigheid
      REMOVE mutatietype
      REMOVE hoogteniveau
      REMOVE hoogte
      REMOVE nummer
      REMOVE breedte
      REMOVE soortnaam
      REMOVE naam
      REMOVE objectbegintijd
      REMOVE tijdstipregistratie
      REMOVE visualisatiecode
      REMOVE tdncode
      REMOVE id
      SET_TO type = inrichtingselementlijn_@Value(typeinrichtingselement)
    -> AttributeManager_31
TestFilter_13
    DEFAULT_VALUE = <UNFILTERED>
    PASSED_TEST_GROUP_OUTPUT = FIRST
    TEST_LIST:
      "BOOL_OP,OR,COMPOSITE_TEST,""""""1 OR 2 OR 3"""""",TEST_CLAUSE,TEST @Value(fysiekvoorkomen) = op vast deel van brug
      TEST @Value(fysiekvoorkomen) = op beweegbaar deel van brug
      TEST @Value(fysiekvoorkomen) = in tunnel",@Value(fysiekvoorkomen) = op vast deel van brug
    <UNFILTERED> -> Dissolver_6
Dissolver_6
    ACCUM_INPUT_ATTRS = Use Attributes From One Feature
    CLEANING_TOLERANCE = Automatic
    CONNECT_Z_MODE = First Wins
    DEAGGREGATE_INPUT = Yes
    GROUP_BY = filename_10k typelandgebruik
    AREA -> AttributeManager_19
AttributeManager_19
    ATTR_TABLE:
      REMOVE namespace
      REMOVE lokaalid
      REMOVE brontype
      REMOVE bronactualiteit
      REMOVE bronbeschrijving
      REMOVE bronnauwkeurigheid
      REMOVE mutatietype
      REMOVE fysiekvoorkomen
      REMOVE voorkomen
      REMOVE hoogteniveau
      REMOVE naam
      REMOVE objectbegintijd
      REMOVE tijdstipregistratie
      REMOVE visualisatiecode
      REMOVE tdncode
      REMOVE id
      SET_TO type = terrein_@Value(typelandgebruik)
    -> AttributeManager_31
TestFilter_12
    DEFAULT_VALUE = <UNFILTERED>
    PASSED_TEST_GROUP_OUTPUT = FIRST
    TEST_LIST = "BOOL_OP,OR,COMPOSITE_TEST,""""""1"""""",TEST_CLAUSE,TEST @Value(fysiekvoorkomen) = op brug",@Value(fysiekvoorkomen) = op brug
    <UNFILTERED> -> AttributeManager_15
AttributeManager_15
    ATTR_TABLE:
      REMOVE namespace
      REMOVE lokaalid
      REMOVE brontype
      REMOVE bronactualiteit
      REMOVE bronbeschrijving
      REMOVE bronnauwkeurigheid
      REMOVE mutatietype
      REMOVE typewater
      REMOVE breedteklasse
      REMOVE hoofdafwatering
      REMOVE fysiekvoorkomen
      REMOVE voorkomen
      REMOVE hoogteniveau
      REMOVE functie
      REMOVE getijdeinvloed
      REMOVE vaarwegklasse
      REMOVE naamofficieel
      REMOVE naamnl
      REMOVE naamfries
      REMOVE isbagnaam
      REMOVE sluisnaam
      REMOVE brugnaam
      REMOVE objectbegintijd
      REMOVE tijdstipregistratie
      REMOVE visualisatiecode
      REMOVE tdncode
      REMOVE id
      SET_TO type = waterhartlijn
    -> AttributeManager_31
TestFilter_11
    DEFAULT_VALUE = <UNFILTERED>
    PASSED_TEST_GROUP_OUTPUT = FIRST
    TEST_LIST = "BOOL_OP,OR,COMPOSITE_TEST,""""""1"""""",TEST_CLAUSE,TEST @Value(fysiekvoorkomen) = op brug",@Value(fysiekvoorkomen) = op brug
    <UNFILTERED> -> Dissolver_4
Dissolver_4
    ACCUM_INPUT_ATTRS = Use Attributes From One Feature
    CLEANING_TOLERANCE = Automatic
    CONNECT_Z_MODE = First Wins
    DEAGGREGATE_INPUT = Yes
    GROUP_BY = filename_10k
    AREA -> AttributeManager_3
AttributeManager_3
    ATTR_TABLE:
      REMOVE namespace
      REMOVE lokaalid
      REMOVE brontype
      REMOVE bronactualiteit
      REMOVE bronbeschrijving
      REMOVE bronnauwkeurigheid
      REMOVE mutatietype
      REMOVE typewater
      REMOVE breedteklasse
      REMOVE hoofdafwatering
      REMOVE fysiekvoorkomen
      REMOVE voorkomen
      REMOVE hoogteniveau
      REMOVE functie
      REMOVE getijdeinvloed
      REMOVE vaarwegklasse
      REMOVE naamofficieel
      REMOVE naamnl
      REMOVE naamfries
      REMOVE isbagnaam
      REMOVE sluisnaam
      REMOVE brugnaam
      REMOVE objectbegintijd
      REMOVE tijdstipregistratie
      REMOVE visualisatiecode
      REMOVE tdncode
      REMOVE id
      SET_TO type = watervlak
      SET_TO
    -> AttributeManager_31
TestFilter_7
    DEFAULT_VALUE = <UNFILTERED>
    PASSED_TEST_GROUP_OUTPUT = FIRST
    TEST_LIST:
      "BOOL_OP,OR,COMPOSITE_TEST,""""""1 OR 2 OR 3 OR 4"""""",TEST_CLAUSE,TEST @Value(fysiekvoorkomen) = op vast deel van brug
      TEST @Value(fysiekvoorkomen) = op beweegbaar deel van brug
      TEST @Value(fysiekvoorkomen) = in tunnel
      TEST @Value(typeweg) = veerverbinding",@Value(fysiekvoorkomen) = op vast deel van brug
    <UNFILTERED> -> AttributeManager_12
AttributeManager_12
    ATTR_TABLE:
      REMOVE namespace
      REMOVE lokaalid
      REMOVE brontype
      REMOVE bronactualiteit
      REMOVE bronbeschrijving
      REMOVE bronnauwkeurigheid
      REMOVE mutatietype
      REMOVE typeweg
      REMOVE hoogteniveau
      REMOVE typeinfrastructuur
      REMOVE hoofdverkeersgebruik
      REMOVE fysiekvoorkomen
      REMOVE verhardingsbreedteklasse
      REMOVE verhardingstype
      REMOVE status
      REMOVE isbagnaam
      REMOVE naam
      REMOVE brugnaam
      REMOVE tunnelnaam
      REMOVE objectbegintijd
      REMOVE tijdstipregistratie
      REMOVE visualisatiecode
      REMOVE tdncode
      REMOVE id
      SET_TO type = weghartlijn
      REMOVE gescheidenrijbaan
      REMOVE aantalrijstroken
      REMOVE awegnummer
      REMOVE nwegnummer
      REMOVE ewegnummer
      REMOVE swegnummer
      REMOVE afritnummer
      REMOVE afritnaam
      REMOVE knooppuntnaam
    -> AttributeManager_31
TestFilter_6
    DEFAULT_VALUE = <UNFILTERED>
    PASSED_TEST_GROUP_OUTPUT = FIRST
    TEST_LIST:
      "BOOL_OP,OR,COMPOSITE_TEST,""""""1 OR 2 OR 3 OR 4"""""",TEST_CLAUSE,TEST @Value(fysiekvoorkomen) = op vast deel van brug
      TEST @Value(fysiekvoorkomen) = op beweegbaar deel van brug
      TEST @Value(fysiekvoorkomen) = in tunnel
      TEST @Value(typeweg) = veerverbinding",@Value(fysiekvoorkomen) = op vast deel van brug
    <UNFILTERED> -> AttributeManager_11
AttributeManager_11
    ATTR_TABLE:
      REMOVE namespace
      REMOVE lokaalid
      REMOVE brontype
      REMOVE bronactualiteit
      REMOVE bronbeschrijving
      REMOVE bronnauwkeurigheid
      REMOVE mutatietype
      REMOVE typeweg
      REMOVE hoogteniveau
      REMOVE typeinfrastructuur
      REMOVE hoofdverkeersgebruik
      REMOVE fysiekvoorkomen
      REMOVE verhardingsbreedteklasse
      REMOVE verhardingstype
      REMOVE status
      REMOVE isbagnaam
      REMOVE naam
      REMOVE brugnaam
      REMOVE tunnelnaam
      REMOVE objectbegintijd
      REMOVE tijdstipregistratie
      REMOVE visualisatiecode
      REMOVE tdncode
      REMOVE id
      SET_TO type = weglijn
    -> AttributeManager_31
TestFilter_9
    DEFAULT_VALUE = <UNFILTERED>
    PASSED_TEST_GROUP_OUTPUT = FIRST
    TEST_LIST:
      "BOOL_OP,OR,COMPOSITE_TEST,""""""1 OR 2 OR 3 OR 4"""""",TEST_CLAUSE,TEST @Value(fysiekvoorkomen) = op vast deel van brug
      TEST @Value(fysiekvoorkomen) = op beweegbaar deel van brug
      TEST @Value(fysiekvoorkomen) = in tunnel
      TEST @Value(typeweg) = veerverbinding",@Value(fysiekvoorkomen) = op vast deel van brug
    <UNFILTERED> -> Dissolver_5
Dissolver_5
    ACCUM_INPUT_ATTRS = Use Attributes From One Feature
    CLEANING_TOLERANCE = Automatic
    CONNECT_Z_MODE = First Wins
    DEAGGREGATE_INPUT = Yes
    GROUP_BY = verhardingstype filename_10k
    AREA -> AttributeManager_7
AttributeManager_7
    ATTR_TABLE:
      REMOVE namespace
      REMOVE lokaalid
      REMOVE brontype
      REMOVE bronactualiteit
      REMOVE bronbeschrijving
      REMOVE bronnauwkeurigheid
      REMOVE mutatietype
      REMOVE typeweg
      REMOVE hoogteniveau
      REMOVE typeinfrastructuur
      REMOVE hoofdverkeersgebruik
      REMOVE fysiekvoorkomen
      REMOVE verhardingsbreedteklasse
      REMOVE gescheidenrijbaan
      REMOVE verhardingstype
      REMOVE aantalrijstroken
      REMOVE status
      REMOVE awegnummer
      REMOVE nwegnummer
      REMOVE ewegnummer
      REMOVE swegnummer
      REMOVE afritnummer
      REMOVE afritnaam
      REMOVE isbagnaam
      REMOVE naam
      REMOVE knooppuntnaam
      REMOVE brugnaam
      REMOVE tunnelnaam
      REMOVE objectbegintijd
      REMOVE tijdstipregistratie
      REMOVE visualisatiecode
      REMOVE tdncode
      REMOVE id
      SET_TO type = wegvlak
    -> AttributeManager_31
AttributeManager_31
    ATTR_TABLE:
      REMOVE typelandgebruik
      REMOVE typegebouw
      REMOVE typeinrichtingselement
    -> Chopper_2
Chopper_2
    DEAGGREGATE_INPUT = Deaggregate
    MAX_VERTICES = 2
    MODE = By Vertex
    CHOPPED -> Clipper_2 [CANDIDATE]
    UNTOUCHED -> Clipper_2 [CANDIDATE]
Junction_8
    -> Clipper_2 [CLIPPER]
Clipper_2
    ATTR_ACCUM_MODE = MERGE
    ATTR_CONFLICT_RES = CANDIDATE
    BOUNDARY_CASES = INSIDE
    CLEANING_TOLERANCE = Automatic
    CLIPPERS_FIRST = NO
    GENERATE_LIST = NO
    GROUP_BY = filename_10k
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> GeometryValidator
GeometryValidator
    PRESETS = All
    REPAIR = Yes
    RULES = AREA_ORIENTATION AREA_ORIENTATION]VALID]FME_CONTROLLER_QUERY_FILE]transformers/dependencies/geometryvalidator8/AREA_ORIENTATION.fme]FME_CONTROLLER_CHOICE]AREA_ORIENTATION CONSECUTIVE_IDENTICAL_VERTICES_2D CHECK_Z]YES]TOLERANCE]0.0]FME_CONTROLLER_QUERY_FILE]transformers/dependencies/geometryvalidator8/CONSECUTIVE_IDENTICAL_VERTICES_2D.fme]FME_CONTROLLER_CHOICE]CONSECUTIVE_IDENTICAL_VERTICES_2D MISSING_TEXTURE_COORDINATES FME_CONTROLLER_QUERY_FILE]transformers/dependencies/geometryvalidator8/MISSING_TEXTURE_COORDINATES.fme]FME_CONTROLLER_CHOICE]MISSING_TEXTURE_COORDINATES MISSING_VERTEX_NORMALS FME_CONTROLLER_QUERY_FILE]transformers/dependencies/geometryvalidator8/MISSING_VERTEX_NORMALS.fme]FME_CONTROLLER_CHOICE]MISSING_VERTEX_NORMALS NAN_REMOVAL PROCESS_MEASURE]NO]FME_CONTROLLER_QUERY_FILE]transformers/dependencies/geometryvalidator8/NAN_REMOVAL.fme]FME_CONTROLLER_CHOICE]NAN_REMOVAL NULL_REMOVAL FME_CONTROLLER_QUERY_FILE]transformers/dependencies/geometryvalidator8/NULL_REMOVAL.fme]FME_CONTROLLER_CHOICE]NULL_REMOVAL OGC_SIMPLE_CHECK LEGACY_OGC]No]FME_CONTROLLER_QUERY_FILE]transformers/dependencies/geometryvalidator8/OGC_SIMPLE_CHECK.fme]FME_CONTROLLER_CHOICE]OGC_SIMPLE_CHECK OGC_VALID_CHECK OGC_VERSION]V1.2.0]LEGACY_OGC]No]FME_CONTROLLER_QUERY_FILE]transformers/dependencies/geometryvalidator8/OGC_VALID_CHECK.fme]FME_CONTROLLER_CHOICE]OGC_VALID_CHECK PLANAR_SURFACE CHECK_AREA]DO_NOT_CHECK_AREA]TOLERANCE_MODE]AUTO]TOLERANCE]<Unused>]ANGULAR_TOLERANCE_MODE]AUTO]ANGULAR_TOLERANCE]<Unused>]FME_CONTROLLER_QUERY_FILE]transformers/dependencies/geometryvalidator8/PLANAR_SURFACE.fme]FME_CONTROLLER_CHOICE]PLANAR_SURFACE SELF_INTERSECTING CHECK_HOLE_TOUCHING_POLYGON]No]CONNECT_Z_MODE_SI]FIRST_WINS]SELF_INTERSECTION_TOLERANCE]None]INTERSECT_ACROSS_MULTIS]No]FME_CONTROLLER_QUERY_FILE]transformers/dependencies/geometryvalidator8/SELF_INTERSECTING.fme]FME_CONTROLLER_CHOICE]SELF_INTERSECTING SHELL_VALIDATION FLIP_APPEARANCE_MODE]FLIP_APPEARANCES]FME_CONTROLLER_QUERY_FILE]transformers/dependencies/geometryvalidator8/SHELL_VALIDATION.fme]FME_CONTROLLER_CHOICE]SHELL_VALIDATION SOLID_VOID_REPAIR FME_CONTROLLER_QUERY_FILE]transformers/dependencies/geometryvalidator8/SOLID_VOID_REPAIR.fme]FME_CONTROLLER_CHOICE]SOLID_VOID_REPAIR TYPE_REPAIR CONNECT_Z_MODE]FIRST_WINS]ARC_ENDPOINT_TOLERANCE_MODE]Auto]ARC_ENDPOINT_TOLERANCE]<Unused>]FME_CONTROLLER_QUERY_FILE]transformers/dependencies/geometryvalidator8/TYPE_REPAIR.fme]FME_CONTROLLER_CHOICE]TYPE_REPAIR MISMATCHED_DIMENSIONS FORCE_DIMENSION]2D]MISMATCHED_Z_VAL]<Unused>]FME_CONTROLLER_QUERY_FILE]transformers/dependencies/geometryvalidator8/MISMATCHED_DIMENSIONS.fme]FME_CONTROLLER_CHOICE]MISMATCHED_DIMENSIONS MISSING_MEASURES_AND_ELEVATIONS MISSING_VALUES_MODE]SENTINEL]MISSING_MEASURES_MODE]<Unused>]SENTINEL_VALUE]0]LENGTH_DIMENSION]<Unused>]FME_CONTROLLER_QUERY_FILE]transformers/dependencies/geometryvalidator8/MISSING_MEASURES_AND_ELEVATIONS.fme]FME_CONTROLLER_CHOICE]MISSING_MEASURES_AND_ELEVATIONS SURFACE_ORIENTATION FME_CONTROLLER_QUERY_FILE]transformers/dependencies/geometryvalidator8/SURFACE_ORIENTATION.fme]FME_CONTROLLER_CHOICE]SURFACE_ORIENTATION SOLID_ORIENTATION FME_CONTROLLER_QUERY_FILE]transformers/dependencies/geometryvalidator8/SOLID_ORIENTATION.fme]FME_CONTROLLER_CHOICE]SOLID_ORIENTATION
    SUMMARY = Detailed
    PASSED -> LineOnLineOverlayer_2 [LINE]
    REPAIRED -> LineOnLineOverlayer_2 [LINE]
LineOnLineOverlayer_2
    ATTRS_ACCUM_MODE = Merge Attributes
    CLEANING_TOLERANCE = Automatic
    DEAGGREGATE_INPUT = Yes
    GENERATE_LIST_DROP = YES
    GROUP_BY = filename_10k
    LIST_ATTRS_TO_INCLUDE = type
    LIST_NAME = poly_
    SEPARATE_COLLINEAR_SEGMENTS = No
    LINE -> Counter_4
Counter_4
    CNT_ATTR = topo_id
    DOMAIN = counter
    SCOPE = Global
    START = 0
    -> AttributeManager_6
AttributeManager_6
    ATTR_TABLE:
      REMOVE poly_{}.direction
      SET_TO topo_source = BRT
      REMOVE type
    -> BRT
    -> AttributeManager_35
BRT: Inspector [off]

Bookmark: BGT
FeatureReader_3
    ATTRIBUTES = bgt,"_creation_instance,BeginTijd,EindTijd,IdentificatieNamespace,IdentificatieLokaalID,TijdstipRegistratie,Bronhouder,InOnderzoek,RelatieveHoogteligging,BgtStatus,PlusStatus,BgtType,PlusType,BgtFysiekVoorkomen,PlusFysiekVoorkomen,OpTalud,feature_type,BgtFunctie,Class,DatumInwinning,EindRegistratie,Hoek,InwinnendeInstantie,Inwinningsmethode,LV-publicatiedatum,Naam,Nauwkeurigheid,PlusFunctie,output_file,id"
    ATTR_ACCUM_MODE = Merge Initiator and Result
    ATTR_CONFLICT_RES = Use Result
    ATTR_IGNORE_NULLS = No
    COMBINE_GEOM = Use Result
    DATASET = $(bgt_file)
    FEATURETYPES = bgt
    FORMAT = OGCGEOPACKAGE
    GEOMETRY_TYPES = bgt,""",fme_arc,fme_area,fme_collection,fme_line,fme_point,fme_solid"""
    INTERACT = INTERSECTS
    OGCGEOPACKAGE_ENFORCE_FOREIGN_KEY_INTEGRITY = NO
    OGCGEOPACKAGE_USE_SEARCH_ENVELOPE = NO
    OUTPUT_FEATURES_DISPLAY = Schema and Data Features
    bgt -> GeometryFilter_2
GeometryFilter_2
    FILTER_MODE = SIMPLE
    FILTER_MULTI = FILTER_TYPES]"Curve Area"]FME_CONTROLLER_QUERY_FILE]]FME_CONTROLLER_CHOICE]Simple
    Curve -> TestFilter_2
    Area -> TestFilter_2
TestFilter_2
    DEFAULT_VALUE = <UNFILTERED>
    PASSED_TEST_GROUP_OUTPUT = FIRST
    TEST_LIST:
      "BOOL_OP,AND,COMPOSITE_TEST,""""""1 AND 2 AND 3 AND 4"""""",TEST_CLAUSE,TEST @Value(RelatieveHoogteligging) = 0
      CASE_INSENSITIVE_TEST @Value(BgtType) NOT_LIKE niet-bgt
      CASE_INSENSITIVE_TEST @Value(Class) NOT_LIKE niet-bgt
      CASE_INSENSITIVE_TEST @Value(BgtFunctie) NOT_LIKE niet-bgt",@Value(RelatieveHoogteligging) = 0
    @Value(RelatieveHoogteligging) = 0 -> Tester
Tester
    BOOL_OP = COMPOSITE
    COMPOSITE_TEST = 1 AND 2
    TEST_CLAUSE:
      TEST Class ATTRIBUTE_HAS_A_VALUE ""
      TEST BgtFysiekVoorkomen NOT_ATTRIBUTE_HAS_A_VALUE ""
    TEST_MODE = TEST
    PASSED -> AttributeManager_9
    FAILED -> TestFilter_4
AttributeManager_9
    ATTR_TABLE = REMOVE BgtFysiekVoorkomen
    -> AttributeManager_44
AttributeManager_44
    ATTR_TABLE = RENAME_SET_VALUE Class > BgtFysiekVoorkomen
    -> TestFilter_4
TestFilter_4
    DEFAULT_VALUE = <UNFILTERED>
    PASSED_TEST_GROUP_OUTPUT = FIRST
    TEST_LIST = "BOOL_OP,OR,COMPOSITE_TEST,""""""1"""""",TEST_CLAUSE,TEST @Value(feature_type) = pand",@Value(feature_type) = pand,"BOOL_OP,OR,COMPOSITE_TEST,""""""1"""""",TEST_CLAUSE,TEST @Value(feature_type) = overigbouwwerk",@Value(feature_type) = overigbouwwerk,"BOOL_OP,OR,COMPOSITE_TEST,""""""1"""""",TEST_CLAUSE,TEST @Value(feature_type) = waterdeel",@Value(feature_type) = waterdeel,"BOOL_OP,OR,COMPOSITE_TEST,""""""1"""""",TEST_CLAUSE,TEST @Value(feature_type) = ondersteunendwaterdeel",@Value(feature_type) = ondersteunendwaterdeel,"BOOL_OP,OR,COMPOSITE_TEST,""""""1"""""",TEST_CLAUSE,TEST @Value(feature_type) = wegdeel",@Value(feature_type) = wegdeel,"BOOL_OP,OR,COMPOSITE_TEST,""""""1"""""",TEST_CLAUSE,TEST @Value(feature_type) = ondersteunendwegdeel",@Value(feature_type) = ondersteunendwegdeel,"BOOL_OP,OR,COMPOSITE_TEST,""""""1"""""",TEST_CLAUSE,TEST @Value(feature_type) = scheiding",@Value(feature_type) = scheiding,"BOOL_OP,OR,COMPOSITE_TEST,""""""1"""""",TEST_CLAUSE,TEST @Value(feature_type) = begroeidterreindeel",@Value(feature_type) = begroeidterreindeel,"BOOL_OP,OR,COMPOSITE_TEST,""""""1"""""",TEST_CLAUSE,TEST @Value(feature_type) = onbegroeidterreindeel",@Value(feature_type) = onbegroeidterreindeel,"BOOL_OP,OR,COMPOSITE_TEST,""""""1"""""",TEST_CLAUSE,TEST @Value(feature_type) = Kunstwerkdeel",@Value(feature_type) = kunstwerkdeel,"BOOL_OP,OR,COMPOSITE_TEST,""""""1"""""",TEST_CLAUSE,TEST @Value(feature_type) = spoor",@Value(feature_type) = spoor
    @Value(feature_type) = pand -> AttributeManager_38
    @Value(feature_type) = overigbouwwerk -> AttributeManager_43
    @Value(feature_type) = waterdeel -> Dissolver_7
    @Value(feature_type) = ondersteunendwaterdeel -> Dissolver_7
    @Value(feature_type) = wegdeel -> Dissolver_8
    @Value(feature_type) = ondersteunendwegdeel -> Dissolver_9
    @Value(feature_type) = scheiding -> AttributeManager_42
    @Value(feature_type) = begroeidterreindeel -> Dissolver
    @Value(feature_type) = onbegroeidterreindeel -> Dissolver_3
    @Value(feature_type) = kunstwerkdeel -> AttributeManager_41
    @Value(feature_type) = spoor -> AttributeManager_38
Dissolver_3
    ACCUM_INPUT_ATTRS = Use Attributes From One Feature
    CLEANING_TOLERANCE = Automatic
    CONNECT_Z_MODE = First Wins
    DEAGGREGATE_INPUT = Yes
    GROUP_BY = BgtFysiekVoorkomen feature_type filename_10k
    AREA -> AttributeManager_13
    <REJECTED> -> AttributeManager_13
AttributeManager_13
    ATTR_TABLE = SET_TO type_type = @Value(feature_type)_@Value(BgtFysiekVoorkomen)
    -> AttributeManager_16
Dissolver
    ACCUM_INPUT_ATTRS = Use Attributes From One Feature
    CLEANING_TOLERANCE = Automatic
    CONNECT_Z_MODE = First Wins
    DEAGGREGATE_INPUT = Yes
    GROUP_BY = feature_type filename_10k BgtFysiekVoorkomen
    AREA -> AttributeManager_28
    <REJECTED> -> AttributeManager_28
AttributeManager_28
    ATTR_TABLE = SET_TO type_type = @Value(feature_type)_@Value(BgtFysiekVoorkomen)
    -> AttributeManager_16
Dissolver_7
    ACCUM_INPUT_ATTRS = Use Attributes From One Feature
    CLEANING_TOLERANCE = Automatic
    CONNECT_Z_MODE = First Wins
    DEAGGREGATE_INPUT = Yes
    GROUP_BY = feature_type filename_10k
    AREA -> AttributeManager_38
    <REJECTED> -> AttributeManager_38
AttributeManager_38
    ATTR_TABLE = SET_TO type_type = @Value(feature_type)
    -> AttributeManager_16
AttributeManager_43
    ATTR_TABLE = SET_TO type_type = @Value(feature_type)_@Value(BgtType)
    -> AttributeManager_16
AttributeManager_42
    ATTR_TABLE = SET_TO type_type = @Value(feature_type)_@Value(BgtType)
    -> AttributeManager_16
AttributeManager_41
    ATTR_TABLE = SET_TO type_type = @Value(feature_type)_@Value(BgtType)
    -> AttributeManager_16
Dissolver_9
    ACCUM_INPUT_ATTRS = Use Attributes From One Feature
    CLEANING_TOLERANCE = Automatic
    CONNECT_Z_MODE = First Wins
    DEAGGREGATE_INPUT = Yes
    GROUP_BY = BgtFysiekVoorkomen feature_type filename_10k
    AREA -> AttributeManager_39
    <REJECTED> -> AttributeManager_39
AttributeManager_39
    ATTR_TABLE = SET_TO type_type = @Value(feature_type)_@Value(BgtFysiekVoorkomen)
    -> AttributeManager_16
Dissolver_8
    ACCUM_INPUT_ATTRS = Use Attributes From One Feature
    CLEANING_TOLERANCE = Automatic
    CONNECT_Z_MODE = First Wins
    DEAGGREGATE_INPUT = Yes
    GROUP_BY = BgtFysiekVoorkomen feature_type filename_10k
    AREA -> AttributeManager_40
    <REJECTED> -> AttributeManager_40
AttributeManager_40
    ATTR_TABLE = SET_TO type_type = @Value(feature_type)_@Value(BgtFysiekVoorkomen)
    -> AttributeManager_16
AttributeManager_16
    ATTR_TABLE:
      REMOVE _creation_instance
      REMOVE BeginTijd
      REMOVE EindTijd
      REMOVE IdentificatieNamespace
      REMOVE IdentificatieLokaalID
      REMOVE TijdstipRegistratie
      REMOVE Bronhouder
      REMOVE InOnderzoek
      REMOVE RelatieveHoogteligging
      REMOVE BgtStatus
      REMOVE PlusStatus
      REMOVE BgtType
      REMOVE PlusType
      REMOVE BgtFysiekVoorkomen
      REMOVE PlusFysiekVoorkomen
      REMOVE OpTalud
      REMOVE feature_type
      REMOVE BgtFunctie
      REMOVE Class
      REMOVE DatumInwinning
      REMOVE EindRegistratie
      REMOVE Hoek
      REMOVE InwinnendeInstantie
      REMOVE Inwinningsmethode
      REMOVE LV-publicatiedatum
      REMOVE Naam
      REMOVE Nauwkeurigheid
      REMOVE PlusFunctie
      REMOVE output_file
      REMOVE fme_rejection_code
      RENAME_SET_VALUE type_type > type
    USER_EXPOSED_ATTRIBUTES = tile
    -> StringReplacer_3
StringReplacer_3
    CASE = NO
    FIND_TEXT = _waardeOnbekend
    NO_MATCH = _FME_NO_OP_
    REGEXP = NO
    SRC_ATTRS = type
    -> Chopper
Chopper
    DEAGGREGATE_INPUT = Deaggregate
    MAX_VERTICES = 2
    MODE = By Vertex
    CHOPPED -> Clipper_3 [CANDIDATE]
    UNTOUCHED -> Clipper_3 [CANDIDATE]
Junction_22
    -> Clipper_3 [CLIPPER]
Clipper_3
    ATTR_ACCUM_MODE = MERGE
    ATTR_CONFLICT_RES = CANDIDATE
    BOUNDARY_CASES = INSIDE
    CLEANING_TOLERANCE = Automatic
    CLIPPERS_FIRST = NO
    GENERATE_LIST = NO
    GROUP_BY = filename_10k
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> GeometryValidator_2
GeometryValidator_2
    PRESETS = All
    REPAIR = Yes
    RULES = AREA_ORIENTATION AREA_ORIENTATION]VALID]FME_CONTROLLER_QUERY_FILE]transformers/dependencies/geometryvalidator8/AREA_ORIENTATION.fme]FME_CONTROLLER_CHOICE]AREA_ORIENTATION CONSECUTIVE_IDENTICAL_VERTICES_2D CHECK_Z]YES]TOLERANCE]0.0]FME_CONTROLLER_QUERY_FILE]transformers/dependencies/geometryvalidator8/CONSECUTIVE_IDENTICAL_VERTICES_2D.fme]FME_CONTROLLER_CHOICE]CONSECUTIVE_IDENTICAL_VERTICES_2D MISSING_TEXTURE_COORDINATES FME_CONTROLLER_QUERY_FILE]transformers/dependencies/geometryvalidator8/MISSING_TEXTURE_COORDINATES.fme]FME_CONTROLLER_CHOICE]MISSING_TEXTURE_COORDINATES MISSING_VERTEX_NORMALS FME_CONTROLLER_QUERY_FILE]transformers/dependencies/geometryvalidator8/MISSING_VERTEX_NORMALS.fme]FME_CONTROLLER_CHOICE]MISSING_VERTEX_NORMALS NAN_REMOVAL PROCESS_MEASURE]NO]FME_CONTROLLER_QUERY_FILE]transformers/dependencies/geometryvalidator8/NAN_REMOVAL.fme]FME_CONTROLLER_CHOICE]NAN_REMOVAL NULL_REMOVAL FME_CONTROLLER_QUERY_FILE]transformers/dependencies/geometryvalidator8/NULL_REMOVAL.fme]FME_CONTROLLER_CHOICE]NULL_REMOVAL OGC_SIMPLE_CHECK LEGACY_OGC]No]FME_CONTROLLER_QUERY_FILE]transformers/dependencies/geometryvalidator8/OGC_SIMPLE_CHECK.fme]FME_CONTROLLER_CHOICE]OGC_SIMPLE_CHECK OGC_VALID_CHECK OGC_VERSION]V1.2.0]LEGACY_OGC]No]FME_CONTROLLER_QUERY_FILE]transformers/dependencies/geometryvalidator8/OGC_VALID_CHECK.fme]FME_CONTROLLER_CHOICE]OGC_VALID_CHECK PLANAR_SURFACE CHECK_AREA]DO_NOT_CHECK_AREA]TOLERANCE_MODE]AUTO]TOLERANCE]<Unused>]ANGULAR_TOLERANCE_MODE]AUTO]ANGULAR_TOLERANCE]<Unused>]FME_CONTROLLER_QUERY_FILE]transformers/dependencies/geometryvalidator8/PLANAR_SURFACE.fme]FME_CONTROLLER_CHOICE]PLANAR_SURFACE SELF_INTERSECTING CHECK_HOLE_TOUCHING_POLYGON]No]CONNECT_Z_MODE_SI]FIRST_WINS]SELF_INTERSECTION_TOLERANCE]None]INTERSECT_ACROSS_MULTIS]No]FME_CONTROLLER_QUERY_FILE]transformers/dependencies/geometryvalidator8/SELF_INTERSECTING.fme]FME_CONTROLLER_CHOICE]SELF_INTERSECTING SHELL_VALIDATION FLIP_APPEARANCE_MODE]FLIP_APPEARANCES]FME_CONTROLLER_QUERY_FILE]transformers/dependencies/geometryvalidator8/SHELL_VALIDATION.fme]FME_CONTROLLER_CHOICE]SHELL_VALIDATION SOLID_VOID_REPAIR FME_CONTROLLER_QUERY_FILE]transformers/dependencies/geometryvalidator8/SOLID_VOID_REPAIR.fme]FME_CONTROLLER_CHOICE]SOLID_VOID_REPAIR TYPE_REPAIR CONNECT_Z_MODE]FIRST_WINS]ARC_ENDPOINT_TOLERANCE_MODE]Auto]ARC_ENDPOINT_TOLERANCE]<Unused>]FME_CONTROLLER_QUERY_FILE]transformers/dependencies/geometryvalidator8/TYPE_REPAIR.fme]FME_CONTROLLER_CHOICE]TYPE_REPAIR MISMATCHED_DIMENSIONS FORCE_DIMENSION]2D]MISMATCHED_Z_VAL]<Unused>]FME_CONTROLLER_QUERY_FILE]transformers/dependencies/geometryvalidator8/MISMATCHED_DIMENSIONS.fme]FME_CONTROLLER_CHOICE]MISMATCHED_DIMENSIONS MISSING_MEASURES_AND_ELEVATIONS MISSING_VALUES_MODE]SENTINEL]MISSING_MEASURES_MODE]<Unused>]SENTINEL_VALUE]0]LENGTH_DIMENSION]<Unused>]FME_CONTROLLER_QUERY_FILE]transformers/dependencies/geometryvalidator8/MISSING_MEASURES_AND_ELEVATIONS.fme]FME_CONTROLLER_CHOICE]MISSING_MEASURES_AND_ELEVATIONS SURFACE_ORIENTATION FME_CONTROLLER_QUERY_FILE]transformers/dependencies/geometryvalidator8/SURFACE_ORIENTATION.fme]FME_CONTROLLER_CHOICE]SURFACE_ORIENTATION SOLID_ORIENTATION FME_CONTROLLER_QUERY_FILE]transformers/dependencies/geometryvalidator8/SOLID_ORIENTATION.fme]FME_CONTROLLER_CHOICE]SOLID_ORIENTATION
    SUMMARY = Detailed
    PASSED -> LineOnLineOverlayer_4 [LINE]
LineOnLineOverlayer_4
    ATTRS_ACCUM_MODE = Merge Attributes
    CLEANING_TOLERANCE = Automatic
    DEAGGREGATE_INPUT = Yes
    GENERATE_LIST_DROP = YES
    GROUP_BY = filename_10k
    LIST_ATTRS_TO_INCLUDE = type
    LIST_NAME = poly_
    SEPARATE_COLLINEAR_SEGMENTS = No
    LINE -> Counter_5
Counter_5
    CNT_ATTR = topo_id
    DOMAIN = counter
    SCOPE = Global
    START = 0
    -> AttributeManager_32
AttributeManager_32
    ATTR_TABLE:
      REMOVE poly_{}.direction
      REMOVE type
      SET_TO topo_source = BGT
    USER_EXPOSED_ATTRIBUTES = tile
    -> BGT
    -> Junction_17
Junction_17
    -> Junction_18
BGT: Inspector [off]

Bookmark: BRP
FeatureReader_4
    ATTRIBUTES = brp_gewas,"category,gewas,gewascode,jaar,status"
    ATTR_ACCUM_MODE = Merge Initiator and Result
    ATTR_CONFLICT_RES = Use Result
    ATTR_IGNORE_NULLS = No
    COMBINE_GEOM = Use Result
    DATASET = $(brp_file)
    FEATURETYPES = brp_gewas
    FORMAT = OGCGEOPACKAGE
    GEOMETRY_TYPES = brp_gewas,""",fme_area"""
    INTERACT = INTERSECTS
    OGCGEOPACKAGE_ENFORCE_FOREIGN_KEY_INTEGRITY = NO
    OGCGEOPACKAGE_USE_SEARCH_ENVELOPE = NO
    OUTPUT_FEATURES_DISPLAY = Schema and Data Features
    brp_gewas -> AttributeManager_34
AttributeManager_34
    ATTR_TABLE:
      REMOVE category
      REMOVE gewascode
      REMOVE jaar
      REMOVE status
      SET_TO type = gewasperceel_@Value(gewas)
    -> AttributeManager_45
AttributeManager_45
    ATTR_TABLE = REMOVE gewas
    -> Chopper_3
Chopper_3
    DEAGGREGATE_INPUT = Deaggregate
    MAX_VERTICES = 2
    MODE = By Vertex
    CHOPPED -> Clipper_4 [CANDIDATE]
    UNTOUCHED -> Clipper_4 [CANDIDATE]
Junction_24
    -> Clipper_4 [CLIPPER]
Clipper_4
    ATTR_ACCUM_MODE = MERGE
    ATTR_CONFLICT_RES = CANDIDATE
    BOUNDARY_CASES = INSIDE
    CLEANING_TOLERANCE = Automatic
    CLIPPERS_FIRST = NO
    GENERATE_LIST = NO
    GROUP_BY = filename_10k
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> GeometryValidator_3
GeometryValidator_3
    PRESETS = All
    REPAIR = Yes
    RULES = AREA_ORIENTATION AREA_ORIENTATION]VALID]FME_CONTROLLER_QUERY_FILE]transformers/dependencies/geometryvalidator8/AREA_ORIENTATION.fme]FME_CONTROLLER_CHOICE]AREA_ORIENTATION CONSECUTIVE_IDENTICAL_VERTICES_2D CHECK_Z]YES]TOLERANCE]0.0]FME_CONTROLLER_QUERY_FILE]transformers/dependencies/geometryvalidator8/CONSECUTIVE_IDENTICAL_VERTICES_2D.fme]FME_CONTROLLER_CHOICE]CONSECUTIVE_IDENTICAL_VERTICES_2D MISSING_TEXTURE_COORDINATES FME_CONTROLLER_QUERY_FILE]transformers/dependencies/geometryvalidator8/MISSING_TEXTURE_COORDINATES.fme]FME_CONTROLLER_CHOICE]MISSING_TEXTURE_COORDINATES MISSING_VERTEX_NORMALS FME_CONTROLLER_QUERY_FILE]transformers/dependencies/geometryvalidator8/MISSING_VERTEX_NORMALS.fme]FME_CONTROLLER_CHOICE]MISSING_VERTEX_NORMALS NAN_REMOVAL PROCESS_MEASURE]NO]FME_CONTROLLER_QUERY_FILE]transformers/dependencies/geometryvalidator8/NAN_REMOVAL.fme]FME_CONTROLLER_CHOICE]NAN_REMOVAL NULL_REMOVAL FME_CONTROLLER_QUERY_FILE]transformers/dependencies/geometryvalidator8/NULL_REMOVAL.fme]FME_CONTROLLER_CHOICE]NULL_REMOVAL OGC_SIMPLE_CHECK LEGACY_OGC]No]FME_CONTROLLER_QUERY_FILE]transformers/dependencies/geometryvalidator8/OGC_SIMPLE_CHECK.fme]FME_CONTROLLER_CHOICE]OGC_SIMPLE_CHECK OGC_VALID_CHECK OGC_VERSION]V1.2.0]LEGACY_OGC]No]FME_CONTROLLER_QUERY_FILE]transformers/dependencies/geometryvalidator8/OGC_VALID_CHECK.fme]FME_CONTROLLER_CHOICE]OGC_VALID_CHECK PLANAR_SURFACE CHECK_AREA]DO_NOT_CHECK_AREA]TOLERANCE_MODE]AUTO]TOLERANCE]<Unused>]ANGULAR_TOLERANCE_MODE]AUTO]ANGULAR_TOLERANCE]<Unused>]FME_CONTROLLER_QUERY_FILE]transformers/dependencies/geometryvalidator8/PLANAR_SURFACE.fme]FME_CONTROLLER_CHOICE]PLANAR_SURFACE SELF_INTERSECTING CHECK_HOLE_TOUCHING_POLYGON]No]CONNECT_Z_MODE_SI]FIRST_WINS]SELF_INTERSECTION_TOLERANCE]None]INTERSECT_ACROSS_MULTIS]No]FME_CONTROLLER_QUERY_FILE]transformers/dependencies/geometryvalidator8/SELF_INTERSECTING.fme]FME_CONTROLLER_CHOICE]SELF_INTERSECTING SHELL_VALIDATION FLIP_APPEARANCE_MODE]FLIP_APPEARANCES]FME_CONTROLLER_QUERY_FILE]transformers/dependencies/geometryvalidator8/SHELL_VALIDATION.fme]FME_CONTROLLER_CHOICE]SHELL_VALIDATION SOLID_VOID_REPAIR FME_CONTROLLER_QUERY_FILE]transformers/dependencies/geometryvalidator8/SOLID_VOID_REPAIR.fme]FME_CONTROLLER_CHOICE]SOLID_VOID_REPAIR TYPE_REPAIR CONNECT_Z_MODE]FIRST_WINS]ARC_ENDPOINT_TOLERANCE_MODE]Auto]ARC_ENDPOINT_TOLERANCE]<Unused>]FME_CONTROLLER_QUERY_FILE]transformers/dependencies/geometryvalidator8/TYPE_REPAIR.fme]FME_CONTROLLER_CHOICE]TYPE_REPAIR MISMATCHED_DIMENSIONS FORCE_DIMENSION]2D]MISMATCHED_Z_VAL]<Unused>]FME_CONTROLLER_QUERY_FILE]transformers/dependencies/geometryvalidator8/MISMATCHED_DIMENSIONS.fme]FME_CONTROLLER_CHOICE]MISMATCHED_DIMENSIONS MISSING_MEASURES_AND_ELEVATIONS MISSING_VALUES_MODE]SENTINEL]MISSING_MEASURES_MODE]<Unused>]SENTINEL_VALUE]0]LENGTH_DIMENSION]<Unused>]FME_CONTROLLER_QUERY_FILE]transformers/dependencies/geometryvalidator8/MISSING_MEASURES_AND_ELEVATIONS.fme]FME_CONTROLLER_CHOICE]MISSING_MEASURES_AND_ELEVATIONS SURFACE_ORIENTATION FME_CONTROLLER_QUERY_FILE]transformers/dependencies/geometryvalidator8/SURFACE_ORIENTATION.fme]FME_CONTROLLER_CHOICE]SURFACE_ORIENTATION SOLID_ORIENTATION FME_CONTROLLER_QUERY_FILE]transformers/dependencies/geometryvalidator8/SOLID_ORIENTATION.fme]FME_CONTROLLER_CHOICE]SOLID_ORIENTATION
    SUMMARY = Detailed
    PASSED -> LineOnLineOverlayer_5 [LINE]
    REPAIRED -> LineOnLineOverlayer_5 [LINE]
LineOnLineOverlayer_5
    ATTRS_ACCUM_MODE = Use Attributes From One Feature
    CLEANING_TOLERANCE = Automatic
    DEAGGREGATE_INPUT = Yes
    GENERATE_LIST_DROP = YES
    GROUP_BY = filename_10k
    LIST_ATTRS_TO_INCLUDE = type
    LIST_NAME = poly_
    SEPARATE_COLLINEAR_SEGMENTS = No
    LINE -> Counter_2
Counter_2
    CNT_ATTR = topo_id
    DOMAIN = counter
    SCOPE = Global
    START = 0
    -> AttributeManager_33
AttributeManager_33
    ATTR_TABLE:
      REMOVE type
      REMOVE poly_{}.direction
      SET_TO topo_source = BRP
    -> BRP
    -> Junction_19
Junction_19
    -> Junction_20
BRP: Inspector [off]

Bookmark: BAG
FeatureReader_6
    ATTRIBUTES = ligplaats,"rdf_seealso,identificatie,status,openbare_ruimte_naam,openbare_ruimte_naam_kort,huisnummer,huisletter,toevoeging,postcode,woonplaats_naam,nummeraanduiding_hoofdadres_identificatie,openbare_ruimte_identificatie,woonplaats_identificatie,bronhouder_identificatie",pand,"rdf_seealso,identificatie,bouwjaar,status,gebruiksdoel,oppervlakte_min,oppervlakte_max,aantal_verblijfsobjecten",standplaats,"rdf_seealso,identificatie,status,openbare_ruimte_naam,openbare_ruimte_naam_kort,huisnummer,huisletter,toevoeging,postcode,woonplaats_naam,nummeraanduiding_hoofdadres_identificatie,openbare_ruimte_identificatie,woonplaats_identificatie,bronhouder_identificatie",verblijfsobject,"rdf_seealso,identificatie,oppervlakte,status,gebruiksdoel,openbare_ruimte_naam,openbare_ruimte_naam_kort,huisnummer,huisletter,toevoeging,postcode,woonplaats_naam,bouwjaar,pand_identificatie,pandstatus,nummeraanduiding_hoofdadres_identificatie,openbare_ruimte_identificatie,woonplaats_identificatie,bronhouder_identificatie",woonplaats,"rdf_seealso,identificatie,status,woonplaats,bronhouder_identificatie"
    ATTR_ACCUM_MODE = Merge Initiator and Result
    ATTR_CONFLICT_RES = Use Result
    ATTR_IGNORE_NULLS = No
    COMBINE_GEOM = Use Result
    DATASET = $(bag_file)
    FEATURETYPES = pand
    FORMAT = OGCGEOPACKAGE
    GEOMETRY_TYPES = ligplaats,""",fme_area""",pand,""",fme_area""",standplaats,""",fme_area""",verblijfsobject,""",fme_point""",woonplaats,""",fme_area"""
    INTERACT = INTERSECTS
    OGCGEOPACKAGE_ENFORCE_FOREIGN_KEY_INTEGRITY = NO
    OGCGEOPACKAGE_USE_SEARCH_ENVELOPE = NO
    OUTPUT_FEATURES_DISPLAY = Schema and Data Features
    pand -> AttributeManager_36
AttributeManager_36
    ATTR_TABLE:
      REMOVE identificatie
      REMOVE rdf_seealso
      REMOVE bouwjaar
      REMOVE status
      REMOVE gebruiksdoel
      REMOVE oppervlakte_min
      REMOVE oppervlakte_max
      REMOVE aantal_verblijfsobjecten
      SET_TO type = pand
    -> Chopper_5
Chopper_5
    DEAGGREGATE_INPUT = Deaggregate
    MAX_VERTICES = 2
    MODE = By Vertex
    CHOPPED -> Clipper_5 [CANDIDATE]
    UNTOUCHED -> Clipper_5 [CANDIDATE]
Junction_26
    -> Clipper_5 [CLIPPER]
Clipper_5
    ATTR_ACCUM_MODE = MERGE
    ATTR_CONFLICT_RES = CANDIDATE
    BOUNDARY_CASES = INSIDE
    CLEANING_TOLERANCE = Automatic
    CLIPPERS_FIRST = NO
    GENERATE_LIST = NO
    GROUP_BY = filename_10k
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> GeometryValidator_4
GeometryValidator_4
    PRESETS = All
    REPAIR = Yes
    RULES = AREA_ORIENTATION AREA_ORIENTATION]VALID]FME_CONTROLLER_QUERY_FILE]transformers/dependencies/geometryvalidator8/AREA_ORIENTATION.fme]FME_CONTROLLER_CHOICE]AREA_ORIENTATION CONSECUTIVE_IDENTICAL_VERTICES_2D CHECK_Z]YES]TOLERANCE]0.0]FME_CONTROLLER_QUERY_FILE]transformers/dependencies/geometryvalidator8/CONSECUTIVE_IDENTICAL_VERTICES_2D.fme]FME_CONTROLLER_CHOICE]CONSECUTIVE_IDENTICAL_VERTICES_2D MISSING_TEXTURE_COORDINATES FME_CONTROLLER_QUERY_FILE]transformers/dependencies/geometryvalidator8/MISSING_TEXTURE_COORDINATES.fme]FME_CONTROLLER_CHOICE]MISSING_TEXTURE_COORDINATES MISSING_VERTEX_NORMALS FME_CONTROLLER_QUERY_FILE]transformers/dependencies/geometryvalidator8/MISSING_VERTEX_NORMALS.fme]FME_CONTROLLER_CHOICE]MISSING_VERTEX_NORMALS NAN_REMOVAL PROCESS_MEASURE]NO]FME_CONTROLLER_QUERY_FILE]transformers/dependencies/geometryvalidator8/NAN_REMOVAL.fme]FME_CONTROLLER_CHOICE]NAN_REMOVAL NULL_REMOVAL FME_CONTROLLER_QUERY_FILE]transformers/dependencies/geometryvalidator8/NULL_REMOVAL.fme]FME_CONTROLLER_CHOICE]NULL_REMOVAL OGC_SIMPLE_CHECK LEGACY_OGC]No]FME_CONTROLLER_QUERY_FILE]transformers/dependencies/geometryvalidator8/OGC_SIMPLE_CHECK.fme]FME_CONTROLLER_CHOICE]OGC_SIMPLE_CHECK OGC_VALID_CHECK OGC_VERSION]V1.2.0]LEGACY_OGC]No]FME_CONTROLLER_QUERY_FILE]transformers/dependencies/geometryvalidator8/OGC_VALID_CHECK.fme]FME_CONTROLLER_CHOICE]OGC_VALID_CHECK PLANAR_SURFACE CHECK_AREA]DO_NOT_CHECK_AREA]TOLERANCE_MODE]AUTO]TOLERANCE]<Unused>]ANGULAR_TOLERANCE_MODE]AUTO]ANGULAR_TOLERANCE]<Unused>]FME_CONTROLLER_QUERY_FILE]transformers/dependencies/geometryvalidator8/PLANAR_SURFACE.fme]FME_CONTROLLER_CHOICE]PLANAR_SURFACE SELF_INTERSECTING CHECK_HOLE_TOUCHING_POLYGON]No]CONNECT_Z_MODE_SI]FIRST_WINS]SELF_INTERSECTION_TOLERANCE]None]INTERSECT_ACROSS_MULTIS]No]FME_CONTROLLER_QUERY_FILE]transformers/dependencies/geometryvalidator8/SELF_INTERSECTING.fme]FME_CONTROLLER_CHOICE]SELF_INTERSECTING SHELL_VALIDATION FLIP_APPEARANCE_MODE]FLIP_APPEARANCES]FME_CONTROLLER_QUERY_FILE]transformers/dependencies/geometryvalidator8/SHELL_VALIDATION.fme]FME_CONTROLLER_CHOICE]SHELL_VALIDATION SOLID_VOID_REPAIR FME_CONTROLLER_QUERY_FILE]transformers/dependencies/geometryvalidator8/SOLID_VOID_REPAIR.fme]FME_CONTROLLER_CHOICE]SOLID_VOID_REPAIR TYPE_REPAIR CONNECT_Z_MODE]FIRST_WINS]ARC_ENDPOINT_TOLERANCE_MODE]Auto]ARC_ENDPOINT_TOLERANCE]<Unused>]FME_CONTROLLER_QUERY_FILE]transformers/dependencies/geometryvalidator8/TYPE_REPAIR.fme]FME_CONTROLLER_CHOICE]TYPE_REPAIR MISMATCHED_DIMENSIONS FORCE_DIMENSION]2D]MISMATCHED_Z_VAL]<Unused>]FME_CONTROLLER_QUERY_FILE]transformers/dependencies/geometryvalidator8/MISMATCHED_DIMENSIONS.fme]FME_CONTROLLER_CHOICE]MISMATCHED_DIMENSIONS MISSING_MEASURES_AND_ELEVATIONS MISSING_VALUES_MODE]SENTINEL]MISSING_MEASURES_MODE]<Unused>]SENTINEL_VALUE]0]LENGTH_DIMENSION]<Unused>]FME_CONTROLLER_QUERY_FILE]transformers/dependencies/geometryvalidator8/MISSING_MEASURES_AND_ELEVATIONS.fme]FME_CONTROLLER_CHOICE]MISSING_MEASURES_AND_ELEVATIONS SURFACE_ORIENTATION FME_CONTROLLER_QUERY_FILE]transformers/dependencies/geometryvalidator8/SURFACE_ORIENTATION.fme]FME_CONTROLLER_CHOICE]SURFACE_ORIENTATION SOLID_ORIENTATION FME_CONTROLLER_QUERY_FILE]transformers/dependencies/geometryvalidator8/SOLID_ORIENTATION.fme]FME_CONTROLLER_CHOICE]SOLID_ORIENTATION
    SUMMARY = Detailed
    PASSED -> LineOnLineOverlayer [LINE]
    REPAIRED -> LineOnLineOverlayer [LINE]
LineOnLineOverlayer
    ATTRS_ACCUM_MODE = Use Attributes From One Feature
    CLEANING_TOLERANCE = Automatic
    DEAGGREGATE_INPUT = Yes
    GENERATE_LIST_DROP = YES
    GROUP_BY = filename_10k
    LIST_ATTRS_TO_INCLUDE = type
    LIST_NAME = poly_
    SEPARATE_COLLINEAR_SEGMENTS = No
    LINE -> Counter_3
    <REJECTED> -> LineOnLineOverlayer__Rejected_
Counter_3
    CNT_ATTR = topo_id
    DOMAIN = counter
    SCOPE = Global
    START = 0
    -> AttributeManager_37
AttributeManager_37
    ATTR_TABLE:
      REMOVE type
      REMOVE poly_{}.direction
      SET_TO topo_source = BAG
    USER_EXPOSED_ATTRIBUTES = tile
    -> Junction_14
    -> BAG
Junction_14
    -> Junction_21
BAG: Inspector [off]
LineOnLineOverlayer__Rejected_: Inspector

Bookmark: Combine
LengthCalculator_3
    DIM = 2
    LEN_ATTR = clip_length
    MULT = 1
    -> AttributeManager_8
AttributeManager_8
    ATTR_TABLE:
      SET_TO azimuth_diff = @Evaluate(@abs(@Value(topo_azimuth)-@Value(brk_azimuth)))
      SET_TO topo_overlap_length = @Evaluate(@Evaluate((@Value(clip_length)/@Value(brk_length))*100))
      REMOVE fme_basename
    USER_EXPOSED_ATTRIBUTES = filename_1k_brp,_area_brk,PERC_GEMEENTECODE,PERC_SECTIE
    -> TestFilter_8
TestFilter_8
    DEFAULT_VALUE = <UNFILTERED>
    PASSED_TEST_GROUP_OUTPUT = FIRST
    TEST_LIST = "BOOL_OP,AND,COMPOSITE_TEST,""""""1"""""",TEST_CLAUSE,TEST @Value(azimuth_diff) < $(azimuth_threshold)",azimuth diff
    azimuth diff -> GeometryRemover_2
GeometryRemover_2
    REMOVE_COORDSYS = No
    -> TestFilter_5
TestFilter_5
    DEFAULT_VALUE = <UNFILTERED>
    PASSED_TEST_GROUP_OUTPUT = FIRST
    TEST_LIST = "BOOL_OP,AND,COMPOSITE_TEST,""""""1"""""",TEST_CLAUSE,TEST @Value(topo_overlap_length) >= $(overlap)",@Value(overlap) >= overlap_
    @Value(overlap) >= overlap_ -> ListExploder
    @Value(overlap) >= overlap_ -> AttributeManager
AttributeManager
    USER_EXPOSED_ATTRIBUTES = brk_clip_area,topog_{}.poly_{}.type,topog_{}.topo_overlap,topo_overlap
    -> Junction_5
Junction_5
    -> Junction_6
Junction_6
    -> FeatureMerger_2 [SUPPLIER]
FeatureMerger_2
    ATTR_ACCUM_MODE = Merge Supplier
    ATTR_CONFLICT_RES = Use Requestor
    CLEANING_TOLERANCE = Automatic
    CONNECT_Z_MODE = First Wins
    GEOM_TYPE = Build Polygons
    GROUP_BY = filename_10k
    IGNORE_NULLS = No
    JOIN_KEYS = @Value(brk_id) @Value(brk_id) AUTO @Value(filename_10k) @Value(filename_10k) AUTO
    MERGE_TYPE = Attributes Only
    PROCESS_DUPS = YES
    REJECT_NULL_MISSING_KEYS = No
    SUPPLIERS_FIRST = No
    MERGED -> AttributeManager_2
    UNMERGED_REQUESTOR -> FeatureColorSetter
    UNMERGED_REQUESTOR -> FeatureWriter_6 [Inside]
AttributeManager_2
    ATTR_TABLE:
      REMOVE brk_azimuth
      REMOVE azimuth_diff
      REMOVE poly_{}.type
      REMOVE topo_id
      REMOVE topo_azimuth
      REMOVE topo_source
      REMOVE topo_overlap_length
      REMOVE brk_length
      REMOVE clip_length
    USER_EXPOSED_ATTRIBUTES = brk_area,topo_clip_area,topo_overlap
    -> FeatureWriter_7 [Inside]
    -> FeatureColorSetter_2
FeatureWriter_7
    DATASET = $(Output_dir)\@Value(filename_10k)\brk_matched.gpkg
    DATASET_ATTR = _dataset
    FEATURE_TYPE_LIST_ATTR = _feature_types
    FORMAT = OGCGEOPACKAGE
    OGCGEOPACKAGE_COORDINATE_SYSTEM_GRANULARITY = FEATURE_TYPE
    OGCGEOPACKAGE_DESTINATION_DATASETTYPE_VALIDATION = Yes
    OGCGEOPACKAGE_ENCODE_FEATURE_TYPE_AND_ATTR_NAMES = YES
    OGCGEOPACKAGE_ENFORCE_GEOMETRY_COLUMN_CONSTRAINTS = YES
    OGCGEOPACKAGE_EXPOSE_PRIMARY_KEY_ATTRIBUTE = YES
    OGCGEOPACKAGE_OVERWRITE_DATASET = NO
    OGCGEOPACKAGE_TRANSACTION_SIZE = 5000
    OGCGEOPACKAGE_WRITE_NULLS = YES
    TOTAL_FEATURES_WRITTEN_ATTR = _total_features_written
FeatureColorSetter_2 [off]
    COLOR = 0,0.666667,0
    FILL_COLOR = 0,0.666667,0
    MODE = Fixed
    COLORED -> BRK_matched [off]
BRK_matched: Inspector [off]
FeatureColorSetter [off]
    COLOR = 1,0,0
    FILL_COLOR = 1,0,0
    MODE = Fixed
    COLORED -> BRK_unmatched [off]
BRK_unmatched: Inspector [off]
FeatureWriter_6
    DATASET = $(Output_dir)\@Value(filename_10k)\brk_unmatched.gpkg
    DATASET_ATTR = _dataset
    FEATURE_TYPE_LIST_ATTR = _feature_types
    FORMAT = OGCGEOPACKAGE
    OGCGEOPACKAGE_COORDINATE_SYSTEM_GRANULARITY = FEATURE_TYPE
    OGCGEOPACKAGE_DESTINATION_DATASETTYPE_VALIDATION = Yes
    OGCGEOPACKAGE_ENCODE_FEATURE_TYPE_AND_ATTR_NAMES = YES
    OGCGEOPACKAGE_ENFORCE_GEOMETRY_COLUMN_CONSTRAINTS = YES
    OGCGEOPACKAGE_EXPOSE_PRIMARY_KEY_ATTRIBUTE = YES
    OGCGEOPACKAGE_OVERWRITE_DATASET = NO
    OGCGEOPACKAGE_TRANSACTION_SIZE = 5000
    OGCGEOPACKAGE_WRITE_NULLS = YES
    TOTAL_FEATURES_WRITTEN_ATTR = _total_features_written
ListExploder
    ATTR_ACCUM_MODE = Merge List Attributes
    ATTR_CONFLICT_RES = Use List Attribute Values
    LIST_ATTR = poly_{}
    ELEMENTS -> BRK_overlap
    ELEMENTS -> FeatureWriter_2 [Inside]
FeatureWriter_2
    DATASET = $(Output_dir)\@Value(filename_10k)\brk_overlap.gpkg
    DATASET_ATTR = _dataset
    FEATURE_TYPE_LIST_ATTR = _feature_types
    FORMAT = OGCGEOPACKAGE
    OGCGEOPACKAGE_COORDINATE_SYSTEM_GRANULARITY = FEATURE_TYPE
    OGCGEOPACKAGE_DESTINATION_DATASETTYPE_VALIDATION = Yes
    OGCGEOPACKAGE_ENCODE_FEATURE_TYPE_AND_ATTR_NAMES = YES
    OGCGEOPACKAGE_ENFORCE_GEOMETRY_COLUMN_CONSTRAINTS = YES
    OGCGEOPACKAGE_EXPOSE_PRIMARY_KEY_ATTRIBUTE = YES
    OGCGEOPACKAGE_OVERWRITE_DATASET = NO
    OGCGEOPACKAGE_TRANSACTION_SIZE = 5000
    OGCGEOPACKAGE_WRITE_NULLS = YES
    TOTAL_FEATURES_WRITTEN_ATTR = _total_features_written
BRK_overlap: Inspector [off]
