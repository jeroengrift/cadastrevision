FME workspace clipPlanetScope.fmw

Parameters:
- sample_file = D:\PhD\data\vector\sample\sample_tiles_10k_split.gpkg
- country_border = D:\PhD\data\vector\Bestuurlijke_grenzen\bestuurlijkegrenzen.gpkg
- mosaic_file = D:\PhD\source_data\planetscope\20180506_20180512_PlS_480cm_8bit_RD_RGB.tif
- output_dir = D:\PhD\data\benchmark

Note: Script to preprocess the PlanetScope data downloaded from Satellietdataportaal. The script executes the following steps: / 1. read sample tiles / 2. read country border of NL / 3. Read PlanetScope mosaic of NL / 4. Clip the mosaic with the country border / 5. Clip the result of step 4 per tile / 6. Georeference te result of step 5 / 7. Resample the result of step 6 / 8. Write the clipped mosiac per tile to an output directory
Note: PlanetScope and SuperView data have restricted access. Therefore, we cannot share the data directly through the benchmark dataset. / Please follow these steps to prepare the PlanetScope and SuperView data (please be aware that it is a manual process). There are two ways to download the imagery. / 1. Via an online portal: / a. Browse to https://www.spaceoffice.nl/nl/satellietdataportaal/toegang-data/. / b. A detailed manual of the portal is available here: / i. https://www.satellietdataportaal.nl/wp-content/uploads/2022/02/Handleiding-Satellietdataportaal-2021-v4.pdf / ii. https://www.satellietdataportaal.nl/hoe/ / 2. Via an FTP server / a. A detailed manual of the FTP access is available here: https://www.spaceoffice.nl/files/Dataportaal/Handleiding%20toegang%20onbewerkte%20optische%20satellietdata_versie%20okt2020.pdf / For PlanetScope, a mosaic for the whole country of the Netherlands is available. Please select the file with the name: / • 20180506_20180512_PlS_480cm_8bit_RD_RGB.tif / This mosaic acts as a basis for creating the 90 tiles that will be used in the benchmark dataset.

Bookmark: Process
Creator
    GEOMTYPE = Geometry Object
    NUM = 1
    CREATED -> FeatureReader [INITIATOR]
    CREATED -> FeatureReader_3 [INITIATOR]
    CREATED -> FeatureReader_2 [INITIATOR]
Note: Read sample tiles
FeatureReader
    ATTRIBUTES = tiles_copy,"id,landscape,filename_10k,overlap_landscape,overlap_non_urban,overlap_total,shape_leng,split,fid"
    ATTR_ACCUM_MODE = Only Use Result
    COMBINE_GEOM = Use Result
    DATASET = $(sample_file)
    FEATURETYPES = tiles_copy
    FORMAT = OGCGEOPACKAGE
    GEOMETRY_TYPES = tiles_copy,""",fme_area"""
    INTERACT = <No Spatial Filter>
    OGCGEOPACKAGE_ENCODE_FEATURE_TYPE_AND_ATTR_NAMES = YES
    OGCGEOPACKAGE_ENFORCE_FOREIGN_KEY_INTEGRITY = YES
    OGCGEOPACKAGE_EXPOSE_PRIMARY_KEY_ATTRIBUTE = YES
    OGCGEOPACKAGE_OPEN_SINGLE_RASTER_AS_SUBDATASET = YES
    OGCGEOPACKAGE_QUERY_FEATURE_TYPES_FOR_MERGE_FILTERS = Yes
    OGCGEOPACKAGE_READER_REPLACE_INVALID_CHARS = YES
    OGCGEOPACKAGE_READ_BOOLEANS_AS_YES_NO = YES
    OGCGEOPACKAGE_READ_NULLS = YES
    OGCGEOPACKAGE_USE_SEARCH_ENVELOPE = NO
    OUTPUT_FEATURES_DISPLAY = Schema and Data Features
    tiles_copy -> CoordinateExtractor
CoordinateExtractor
    LIST_NAME = _indices
    MODE = All Coordinates
    -> Clipper [CLIPPER]
Note: Read country border
FeatureReader_3
    ATTRIBUTES = gemeenten,"code,gemeentenaam,fid",landsgrens,"code,landsnaam,fid",provincies,"provincienaam,fid"
    ATTR_ACCUM_MODE = Only Use Result
    COMBINE_GEOM = Use Result
    DATASET = $(country_border)
    FEATURETYPES = landsgrens
    FORMAT = OGCGEOPACKAGE
    GEOMETRY_TYPES = gemeenten,""",fme_area""",landsgrens,""",fme_area""",provincies,""",fme_area"""
    INTERACT = NONE
    OGCGEOPACKAGE_ENCODE_FEATURE_TYPE_AND_ATTR_NAMES = YES
    OGCGEOPACKAGE_ENFORCE_FOREIGN_KEY_INTEGRITY = YES
    OGCGEOPACKAGE_EXPOSE_PRIMARY_KEY_ATTRIBUTE = YES
    OGCGEOPACKAGE_OPEN_SINGLE_RASTER_AS_SUBDATASET = YES
    OGCGEOPACKAGE_QUERY_FEATURE_TYPES_FOR_MERGE_FILTERS = Yes
    OGCGEOPACKAGE_READER_REPLACE_INVALID_CHARS = YES
    OGCGEOPACKAGE_READ_BOOLEANS_AS_YES_NO = YES
    OGCGEOPACKAGE_READ_NULLS = YES
    OGCGEOPACKAGE_USE_SEARCH_ENVELOPE = NO
    OUTPUT_FEATURES_DISPLAY = Schema and Data Features
    landsgrens -> Clipper_2 [CLIPPER]
Note: Read country mosaic
FeatureReader_2
    ATTR_ACCUM_MODE = Only Use Result
    COMBINE_GEOM = Use Result
    DATASET = $(mosaic_file)
    FEATURETYPES = GEOTIFF
    FORMAT = GEOTIFF
    GEOTIFF_APPLY_GCPS = NO
    GEOTIFF_FEATURE_TYPE_NAME = FORMAT_NAME
    GEOTIFF_IGNORE_RASTER_TYPE_KEY = No
    GEOTIFF_LENIENT_READ = Yes
    GEOTIFF_NATIVELY_HANDLED_WEBSERVICES = s3connector,azurestorage,google-cloud-storage
    GEOTIFF_PREFER_FILE_CS_UNITS = Yes
    GEOTIFF_READER_META_ATTRIBUTES = fme_dataset fme_basename
    GEOTIFF_READ_OFFSETS_IN_CS_UNITS = No
    GEOTIFF_USE_SEARCH_ENVELOPE = NO
    INTERACT = NONE
    OUTPUT_FEATURES_DISPLAY = Schema and Data Features
    <OTHER> -> Clipper_2 [CANDIDATE]
Clipper_2
    BOUNDARY_CASES = INSIDE
    CLEANING_TOLERANCE = Automatic
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> RasterPropertyExtractor_2
RasterPropertyExtractor_2
    -> RasterSubsetter_2
RasterSubsetter_2
    NUM_BOTTOM_PADDING_ROWS = 10000
    NUM_COLUMNS = @Value(_num_columns)
    NUM_LEFT_PADDDING_COLUMNS = 10000
    NUM_RIGHT_PADDDING_COLUMNS = 10000
    NUM_ROWS = @Value(_num_rows)
    NUM_TOP_PADDING_ROWS = 10000
    START_COLUMN = 0
    START_ROW = 0
    -> Clipper [CANDIDATE]
Clipper
    ATTR_ACCUM_MODE = MERGE
    ATTR_CONFLICT_RES = CANDIDATE
    BOUNDARY_CASES = INSIDE
    CLEANING_TOLERANCE = Automatic
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_ORIGINAL
    PRESERVE_RASTER_EXTENTS = NO
    RASTER_CELL_MODE = BOUNDARY
    Z_VAL_SOURCE = CANDIDATE
    INSIDE -> RasterGeoreferencer
RasterGeoreferencer
    POINTANDANGLE_OR_EXTENTS = Extents
    X_LL_COORD = @Value(_indices{0}.x)
    X_LR_COORD = @Value(_indices{3}.x)
    X_UL_COORD = @Value(_indices{1}.x)
    X_UR_COORD = @Value(_indices{2}.x)
    Y_LL_COORD = @Value(_indices{0}.y)
    Y_LR_COORD = @Value(_indices{3}.y)
    Y_UL_COORD = @Value(_indices{1}.y)
    Y_UR_COORD = @Value(_indices{2}.y)
    -> StringReplacer_4
StringReplacer_4
    CASE = NO
    FIND_TEXT = .tif
    NO_MATCH = _FME_NO_OP_
    REGEXP = NO
    SRC_ATTRS = filename_10k
    -> RasterResampler
RasterResampler
    COLUMNS = 3414
    INTERPOLATION_TYPE_NAME = Nearest Neighbor
    ROWCOL_OR_CELLSIZE = RowsColumns
    ROWS = 3414
    RESAMPLED -> FeatureWriter [Inside]
Note: Set output dir
FeatureWriter
    DATASET = $(output_dir)
    DATASET_ATTR = _dataset
    FEATURE_TYPE_LIST_ATTR = _feature_types
    FORMAT = GEOTIFF
    GEOTIFF_COORDINATE_SYSTEM_GRANULARITY = FEATURE
    GEOTIFF_DESTINATION_DATASETTYPE_VALIDATION = Yes
    GEOTIFF_FORMAT_ATTRIBUTES_OVERRIDE_FEATURE_TYPE_PARAMETERS = Yes
    GEOTIFF_IGNORE_RASTER_TYPE_KEY = No
    GEOTIFF_WRITE_ESRI_COMPATIBLE_COORDSYS = No
    GEOTIFF_WRITE_GEOGRAPHIC_COORDSYS_AS_EPSG_CODE = Yes
    GEOTIFF_WRITE_GEOGRAPHIC_KEYS_FOR_PROJECTED_COORDSYS = Yes
    GEOTIFF_WRITE_OFFSETS_IN_CS_UNITS = Yes
    GEOTIFF_WRITE_PROJECTED_COORDSYS_AS_EPSG_CODE = Yes
    TOTAL_FEATURES_WRITTEN_ATTR = _total_features_written
