FME workspace mosaicSuperView.fmw

Parameters:
- filename = tile-190000-300000.tif
- sample_file = D:\PhD\data\vector\sample\sample_tiles_10k_split.gpkg
- input_dir = D:\PhD\source_data\superview\subtiles   # INCLUDE_WEB_BROWSER input_dir
- output_dir = D:\PhD\data\raster\test_
- country_border = D:\PhD\data\vector\Bestuurlijke_grenzen\bestuurlijkegrenzen.gpkg

Note: Script to preprocess the SuperView data downloaded from Satellietdataportaal. The script executes the following steps: / 1. read sample tiles / 2. Filter on tile name / 3. Select the images that are in the tile dir / 4. Read the images / 5. Mosaic the images / 6. Georeference and resample te images / 7. Write the result to a TIFF file
Note: PlanetScope and SuperView data have restricted access. Therefore, we cannot share the data directly through the benchmark dataset. / Please follow these steps to prepare the PlanetScope and SuperView data (please be aware that it is a manual process). There are two ways to download the imagery. / 1. Via an online portal: / a. Browse to https://www.spaceoffice.nl/nl/satellietdataportaal/toegang-data/. / b. A detailed manual of the portal is available here: / i. https://www.satellietdataportaal.nl/wp-content/uploads/2022/02/Handleiding-Satellietdataportaal-2021-v4.pdf / ii. https://www.satellietdataportaal.nl/hoe/ / 2. Via an FTP server / a. A detailed manual of the FTP access is available here: https://www.spaceoffice.nl/files/Dataportaal/Handleiding%20toegang%20onbewerkte%20optische%20satellietdata_versie%20okt2020.pdf / For SuperView, the preprocessing is more time-consuming because the spatial extents of the SuperView images are smaller than those of the sampled tiles. Please download the following SuperView images in the described directory. Placing the right image in the correct folder is important because this structure creates a mosaic of SuperView images per tile. / • tile-170000-460000\20210331_105746_SV1-03_SV_RD_8bit_RGB_50cm_Kootwijk_lzw.tif / • tile-170000-460000\20220303_101818_SV1-01_SV_RD_8bit_RGB_50cm_Veluwe_lzw.tif / • tile-170000-460000\20210908_112348_SV1-02_SV_RD_8bit_RGB_50cm_Lunteren_lzw.tif / • tile-170000-460000\20220318_110341_SV1-03_SV_RD_8bit_RGB_50cm_Stroe_lzw.tif / • tile-170000-460000\20210331_105748_SV1-03_SV_RD_8bit_RGB_50cm_Ede_lzw.tif / • tile-170000-460000\20210908_112346_SV1-02_SV_RD_8bit_RGB_50cm_Stroe_lzw.tif / • tile-170000-460000\20220303_101820_SV1-01_SV_RD_8bit_RGB_50cm_HogeVeluwe_lzw.tif / • tile-220000-450000\20210416_105012_SV1-01_SV_RD_8bit_RGB_50cm_Zelhem_lzw.tif / • tile-220000-450000\20210602_104841_SV1-03_SV_RD_8bit_RGB_50cm_Groenlo_lzw.tif / • tile-170000-580000\20210416_112828_SV1-02_SV_RD_8bit_RGB_50cm_SintAnnaparochie_lzw.tif / • tile-170000-580000\20210416_112829_SV1-02_SV_RD_8bit_RGB_50cm_Dronrijp_lzw.tif / • tile-170000-580000\20210420_110849_SV1-03_SV_RD_8bit_RGB_50cm_Ferwert_lzw.tif / • tile-170000-580000\20210420_110850_SV1-03_SV_RD_8bit_RGB_50cm_Leeuwarden_lzw.tif / • tile-180000-340000\20220316_101743_SV1-01_SV_RD_8bit_RGB_50cm_MariaHoop_lzw.tif / • tile-180000-340000\20220304_105229_SV1-04_SV_RD_8bit_RGB_50cm_Maaseik_lzw.tif / • tile-210000-560000\20220325_105546_SV1-03_SV_RD_8bit_RGB_50cm_Veenhuizen_lzw.tif / • tile-210000-560000\20220303_101804_SV1-01_SV_RD_8bit_RGB_50cm_Donkerbroek_lzw.tif / • tile-210000-560000\20220313_112521_SV1-02_SV_RD_8bit_RGB_50cm_Bakkeveen_lzw.tif / • tile-210000-560000\20210604_104440_SV1-01_SV_RD_8bit_RGB_50cm_Veenhuizen_lzw.tif / • tile-100000-500000\20210319_111321_SV1-04_SV_RD_8bit_RGB_50cm_Heemskerk_lzw.tif / • tile-100000-500000\20210607_111436_SV1-03_SV_RD_8bit_RGB_50cm_Uitgeest_lzw.tif / • tile-100000-500000\20220302_112103_SV1-04_SV_RD_8bit_RGB_50cm_WijkAanZee_lzw.tif / • tile-190000-350000\20220316_101741_SV1-01_SV_RD_8bit_RGB_50cm_Roermond_lzw.tif / • tile-190000-350000\20220322_102345_SV1-01_SV_RD_8bit_RGB_50cm_MariaHoop_lzw.tif / • tile-190000-350000\20220316_101743_SV1-01_SV_RD_8bit_RGB_50cm_MariaHoop_lzw.tif / • tile-180000-450000\20220303_101820_SV1-01_SV_RD_8bit_RGB_50cm_HogeVeluwe_lzw.tif / • tile-180000-450000\20220309_111346_SV1-04_SV_RD_8bit_RGB_50cm_Eerbeek_lzw.tif / • tile-160000-490000\20220305_110330_SV1-03_SV_RD_8bit_RGB_50cm_Lelystad_lzw.tif / • tile-160000-490000\20220311_111100_SV1-03_SV_RD_8bit_RGB_50cm_Harderwijk_lzw.tif / • tile-160000-490000\20220311_111058_SV1-03_SV_RD_8bit_RGB_50cm_Swifterbant_lzw.tif / • tile-160000-490000\20220305_110332_SV1-03_SV_RD_8bit_RGB_50cm_Zeewolde_lzw.tif / • tile-240000-460000\20220310_105912_SV1-04_SV_RD_8bit_RGB_50cm_Vreden_DE_lzw.tif / • tile-240000-460000\20220310_105910_SV1-04_SV_RD_8bit_RGB_50cm_Buurse_lzw.tif / • tile-240000-460000\20220309_102520_SV1-01_SV_RD_8bit_RGB_50cm_Groenlo_lzw.tif / • tile-240000-460000\20220310_101044_SV1-01_SV_RD_8bit_RGB_50cm_Haaksbergen_lzw.tif / • tile-240000-460000\20220509_104753_SV1-03_SV_RD_8bit_RGB_50cm_Haaksbergen_lzw.tif / • tile-40000-390000\20210610_111724_SV1-04_SV_RD_8bit_RGB_50cm_Goes_lzw.tif / • tile-40000-390000\20210718_111858_SV1-03_SV_RD_8bit_RGB_50cm_Heinkenszand_lzw.tif / • tile-190000-300000\20210428_105454_SV1-03_SV_RD_8bit_RGB_50cm_Epen_lzw.tif / • tile-80000-400000\20220308_104004_SV1-01_SV_RD_8bit_RGB_50cm_Steenbergen_lzw.tif / • tile-80000-400000\20220322_111234_SV1-04_SV_RD_8bit_RGB_50cm_Fijnaart_lzw.tif / • tile-240000-550000\20200404_103924_SV1-01_SV_RD_8bit_RGB_50cm_Gasteren_lzw.tif / • tile-240000-550000\20200404_103926_SV1-01_SV_RD_8bit_RGB_50cm_Assen_lzw.tif / • tile-240000-550000\20200422_110729_SV1-03_SV_RD_8bit_RGB_50cm_Borger_lzw.tif / • tile-180000-540000\20220311_111053_SV1-03_SV_RD_8bit_RGB_50cm_Tjeukemeer_lzw.tif / • tile-180000-540000\20220306_113345_SV1-02_SV_RD_8bit_RGB_50cm_Ossenzijl_lzw.tif / • tile-180000-540000\20220311_111051_SV1-03_SV_RD_8bit_RGB_50cm_Joure_lzw.tif / • tile-220000-530000\20211010_105046_SV1-03_SV_RD_8bit_RGB_50cm_Hoogeveen_lzw.tif / • tile-220000-530000\20210914_113442_SV1-02_SV_RD_8bit_RGB_50cm_Dwingeloo_lzw.tif / • tile-220000-530000\20210914_113444_SV1-02_SV_RD_8bit_RGB_50cm_Ruinen_lzw.tif / • tile-220000-530000\20211010_105044_SV1-03_SV_RD_8bit_RGB_50cm_Beilen_lzw.tif / • tile-180000-320000\20210905_110444_SV1-03_SV_RD_8bit_RGB_50cm_Stein_lzw.tif / • tile-180000-320000\20210723_103546_SV1-01_SV_RD_8bit_RGB_50cm_Valkenburg_lzw.tif / • tile-180000-320000\20210903_102419_SV1-01_SV_RD_8bit_RGB_50cm_Sittard_lzw.tif / • tile-180000-320000\20210905_110446_SV1-03_SV_RD_8bit_RGB_50cm_Maastricht_lzw.tif / • tile-220000-590000\20220303_101759_SV1-01_SV_RD_8bit_RGB_50cm_Waddenzee_lzw.tif / • tile-220000-590000\20220303_101800_SV1-01_SV_RD_8bit_RGB_50cm_Grijpskerk_lzw.tif / • tile-220000-590000\20220313_112515_SV1-02_SV_RD_8bit_RGB_50cm_Pieterburen_lzw.tif / • tile-220000-590000\20220313_112517_SV1-02_SV_RD_8bit_RGB_50cm_Noordhorn_lzw.tif / • tile-60000-430000\20220315_112038_SV1-04_SV_RD_8bit_RGB_50cm_HoekVanHolland_lzw.tif / • tile-60000-430000\20220315_112039_SV1-04_SV_RD_8bit_RGB_50cm_Rockanje_lzw.tif / • tile-120000-580000\20210603_111830_SV1-04_SV_RD_8bit_RGB_50cm_Vlieland_lzw.tif / • tile-120000-580000\20210603_111832_SV1-04_SV_RD_8bit_RGB_50cm_Texel_lzw.tif / • tile-120000-580000\20220308_103937_SV1-01_SV_RD_8bit_RGB_50cm_Waddenzee_lzw.tif / • tile-170000-370000\20220309_111359_SV1-04_SV_RD_8bit_RGB_50cm_Cranendonck_lzw.tif / • tile-170000-370000\20220309_111357_SV1-04_SV_RD_8bit_RGB_50cm_Someren_lzw.tif / • tile-170000-370000\20220313_112612_SV1-02_SV_RD_8bit_RGB_50cm_Weert_lzw.tif / • tile-130000-460000\20220304_111801_SV1-03_SV_RD_8bit_RGB_50cm_Breukelen_lzw.tif / • tile-130000-460000\20220305_114844_SV1-02_SV_RD_8bit_RGB_50cm_Hilversum_lzw.tif / • tile-130000-460000\20220305_114846_SV1-02_SV_RD_8bit_RGB_50cm_Utrecht_lzw.tif / • tile-180000-310000\20210905_110447_SV1-03_SV_RD_8bit_RGB_50cm_Eijsden_lzw.tif / • tile-180000-310000\20210903_102423_SV1-01_SV_RD_8bit_RGB_50cm_Aubel_BE_lzw.tif / • tile-180000-310000\20210905_110446_SV1-03_SV_RD_8bit_RGB_50cm_Maastricht_lzw.tif / • tile-180000-310000\20210903_102421_SV1-01_SV_RD_8bit_RGB_50cm_Valkenburg_lzw.tif / • tile-180000-380000\20210812_104401_SV1-01_SV_RD_8bit_RGB_50cm_IJsselsteyn_lzw.tif / • tile-180000-380000\20210812_104403_SV1-01_SV_RD_8bit_RGB_50cm_Liessel_lzw.tif / • tile-180000-380000\20210825_112842_SV1-02_SV_RD_8bit_RGB_50cm_Gemert_lzw.tif / • tile-210000-540000\20220309_111334_SV1-04_SV_RD_8bit_RGB_50cm_Dwingeloo_lzw.tif / • tile-210000-540000\20220325_105550_SV1-03_SV_RD_8bit_RGB_50cm_Vledder_lzw.tif / • tile-210000-540000\20220325_105548_SV1-03_SV_RD_8bit_RGB_50cm_Oosterwolde_lzw.tif / • tile-30000-410000\20210329_112449_SV1-03_SV_RD_8bit_RGB_50cm_Haamstede_lzw.tif / • tile-30000-410000\20210329_112450_SV1-03_SV_RD_8bit_RGB_50cm_NeeltjeJans_lzw.tif / • tile-160000-550000\20220304_111747_SV1-03_SV_RD_8bit_RGB_50cm_Makkum_lzw.tif / • tile-160000-550000\20220305_114831_SV1-02_SV_RD_8bit_RGB_50cm_Heeg_lzw.tif / • tile-160000-550000\20220304_111749_SV1-03_SV_RD_8bit_RGB_50cm_Hindelopen_lzw.tif / • tile-110000-430000\20220304_111805_SV1-03_SV_RD_8bit_RGB_50cm_Schoonhoven_lzw.tif / • tile-110000-430000\20220303_110649_SV1-04_SV_RD_8bit_RGB_50cm_Moordrecht_lzw.tif / • tile-110000-430000\20210908_104928_SV1-01_SV_RD_8bit_RGB_50cm_Alblasserdam_lzw.tif / • tile-110000-430000\20220304_111807_SV1-03_SV_RD_8bit_RGB_50cm_Sliedrecht_lzw.tif / • tile-190000-320000\20220322_102347_SV1-01_SV_RD_8bit_RGB_50cm_Brunssum_lzw.tif / • tile-190000-320000\20220325_105621_SV1-03_SV_RD_8bit_RGB_50cm_Kerkrade_lzw.tif / • tile-190000-320000\20220322_102349_SV1-01_SV_RD_8bit_RGB_50cm_Heerlen_lzw.tif / • tile-200000-390000\20220322_102338_SV1-01_SV_RD_8bit_RGB_50cm_Arcen_lzw.tif / • tile-200000-390000\20220316_101734_SV1-01_SV_RD_8bit_RGB_50cm_Goch_DE_lzw.tif / • tile-200000-390000\20220316_101736_SV1-01_SV_RD_8bit_RGB_50cm_Horst_lzw.tif / • tile-120000-430000\20220305_114849_SV1-02_SV_RD_8bit_RGB_50cm_Woudrichem_lzw.tif / • tile-120000-430000\20220305_114848_SV1-02_SV_RD_8bit_RGB_50cm_Vianen_lzw.tif / • tile-120000-430000\20220304_111805_SV1-03_SV_RD_8bit_RGB_50cm_Schoonhoven_lzw.tif / • tile-120000-430000\20220304_111807_SV1-03_SV_RD_8bit_RGB_50cm_Sliedrecht_lzw.tif / • tile-150000-420000\20220509_113017_SV1-02_SV_RD_8bit_RGB_50cm_Rossum_lzw.tif / • tile-150000-420000\20220311_111109_SV1-03_SV_RD_8bit_RGB_50cm_Geldermalsen_lzw.tif / • tile-150000-420000\20220311_111110_SV1-03_SV_RD_8bit_RGB_50cm_DenBosch_lzw.tif / • tile-150000-420000\20220509_113015_SV1-02_SV_RD_8bit_RGB_50cm_Dreumel_lzw.tif / • tile-140000-370000\20210601_110234_SV1-03_SV_RD_8bit_RGB_50cm_Middelbeers_lzw.tif / • tile-140000-370000\20210601_110236_SV1-03_SV_RD_8bit_RGB_50cm_Bladel_lzw.tif / • tile-140000-370000\20210618_110202_SV1-04_SV_RD_8bit_RGB_50cm_Bergeijk_lzw.tif / • tile-210000-490000\20220304_105206_SV1-04_SV_RD_8bit_RGB_50cm_Dalfsen_lzw.tif / • tile-210000-490000\20220304_105208_SV1-04_SV_RD_8bit_RGB_50cm_Raalte_lzw.tif / • tile-170000-540000\20220305_110323_SV1-03_SV_RD_8bit_RGB_50cm_Slotermeer_lzw.tif / • tile-170000-540000\20220305_110325_SV1-03_SV_RD_8bit_RGB_50cm_Lemmer_lzw.tif / • tile-140000-420000\20220305_110341_SV1-03_SV_RD_8bit_RGB_50cm_Zaltbommel_lzw.tif / • tile-140000-420000\20220311_111110_SV1-03_SV_RD_8bit_RGB_50cm_DenBosch_lzw.tif / • tile-140000-420000\20220305_110343_SV1-03_SV_RD_8bit_RGB_50cm_Heusden_lzw.tif / • tile-190000-370000\20220515_105135_SV1-03_SV_RD_8bit_RGB_50cm_Meijel_lzw.tif / • tile-190000-370000\20220316_101739_SV1-01_SV_RD_8bit_RGB_50cm_Helden_lzw.tif / • tile-190000-370000\20220304_105224_SV1-04_SV_RD_8bit_RGB_50cm_Meijel_lzw.tif / • tile-190000-370000\20220316_101737_SV1-01_SV_RD_8bit_RGB_50cm_Sevenum_lzw.tif / • tile-230000-450000\20220309_102520_SV1-01_SV_RD_8bit_RGB_50cm_Groenlo_lzw.tif / • tile-230000-450000\20220310_101046_SV1-01_SV_RD_8bit_RGB_50cm_Groenlo_lzw.tif / • tile-230000-450000\20220306_104908_SV1-03_SV_RD_8bit_RGB_50cm_Ruurlo_lzw.tif / • tile-230000-450000\20220509_104754_SV1-03_SV_RD_8bit_RGB_50cm_Meddo_lzw.tif / • tile-150000-600000\20220303_110626_SV1-04_SV_RD_8bit_RGB_50cm_Terschelling_lzw.tif / • tile-150000-600000\20220316_110537_SV1-04_SV_RD_8bit_RGB_50cm_Waddenzee_lzw.tif / • tile-170000-600000\20210330_111040_SV1-03_SV_RD_8bit_RGB_50cm_Ameland_lzw.tif / • tile-170000-600000\20210330_111041_SV1-03_SV_RD_8bit_RGB_50cm_Ameland_lzw.tif / • tile-170000-600000\20210416_112824_SV1-02_SV_RD_8bit_RGB_50cm_Ameland_lzw.tif / • tile-170000-600000\20210416_112826_SV1-02_SV_RD_8bit_RGB_50cm_Waddenzee_lzw.tif / • tile-140000-430000\20220305_110339_SV1-03_SV_RD_8bit_RGB_50cm_WijkBijDuurstede_lzw.tif / • tile-140000-430000\20220508_110305_SV1-03_SV_RD_8bit_RGB_50cm_Everdingen_lzw.tif / • tile-140000-430000\20220311_111109_SV1-03_SV_RD_8bit_RGB_50cm_Geldermalsen_lzw.tif / • tile-140000-430000\20220305_110341_SV1-03_SV_RD_8bit_RGB_50cm_Zaltbommel_lzw.tif / • tile-140000-430000\20220508_110307_SV1-03_SV_RD_8bit_RGB_50cm_Herwijnen_lzw.tif / • tile-190000-450000\20220303_101820_SV1-01_SV_RD_8bit_RGB_50cm_HogeVeluwe_lzw.tif / • tile-190000-450000\20220309_111346_SV1-04_SV_RD_8bit_RGB_50cm_Eerbeek_lzw.tif / • tile-180000-400000\20210812_104401_SV1-01_SV_RD_8bit_RGB_50cm_IJsselsteyn_lzw.tif / • tile-180000-400000\20220309_111353_SV1-04_SV_RD_8bit_RGB_50cm_Volkel_lzw.tif / • tile-180000-400000\20220304_105220_SV1-04_SV_RD_8bit_RGB_50cm_Boxmeer_lzw.tif / • tile-90000-470000\20220308_103955_SV1-01_SV_RD_8bit_RGB_50cm_Leiderdorp_lzw.tif / • tile-90000-470000\20210815_111049_SV1-03_SV_RD_8bit_RGB_50cm_Noordwijkerhout_lzw.tif / • tile-90000-470000\20210815_111051_SV1-03_SV_RD_8bit_RGB_50cm_Oegstgeest_lzw.tif / • tile-100000-470000\20220308_103955_SV1-01_SV_RD_8bit_RGB_50cm_Leiderdorp_lzw.tif / • tile-100000-470000\20220303_110645_SV1-04_SV_RD_8bit_RGB_50cm_Nieuwkoop_lzw.tif / • tile-100000-470000\20220308_103954_SV1-01_SV_RD_8bit_RGB_50cm_NieuwVennep_lzw.tif / • tile-40000-410000\20210302_111341_SV1-03_SV_RD_8bit_RGB_50cm_Brouwersdam_lzw.tif / • tile-40000-410000\20210302_111342_SV1-03_SV_RD_8bit_RGB_50cm_Oosterschelde_lzw.tif / • tile-40000-410000\20210329_112449_SV1-03_SV_RD_8bit_RGB_50cm_Haamstede_lzw.tif / • tile-40000-410000\20210329_112450_SV1-03_SV_RD_8bit_RGB_50cm_NeeltjeJans_lzw.tif / • tile-40000-380000\20210718_111900_SV1-03_SV_RD_8bit_RGB_50cm_Borssele_lzw.tif / • tile-40000-380000\20210718_111858_SV1-03_SV_RD_8bit_RGB_50cm_Heinkenszand_lzw.tif / • tile-40000-380000\20210610_111726_SV1-04_SV_RD_8bit_RGB_50cm_Goes_lzw.tif / • tile-20000-390000\20210329_112452_SV1-03_SV_RD_8bit_RGB_50cm_Middelburg_lzw.tif / • tile-20000-390000\20220321_103842_SV1-01_SV_RD_8bit_RGB_50cm_Westkapelle_lzw.tif / • tile-200000-520000\20220303_101809_SV1-01_SV_RD_8bit_RGB_50cm_Giethoorn_lzw.tif / • tile-200000-520000\20220325_105554_SV1-03_SV_RD_8bit_RGB_50cm_Rouveen_lzw.tif / • tile-200000-520000\20220303_101811_SV1-01_SV_RD_8bit_RGB_50cm_Genemuiden_lzw.tif / • tile-200000-520000\20220325_105552_SV1-03_SV_RD_8bit_RGB_50cm_Meppel_lzw.tif / • tile-170000-550000\20220305_110321_SV1-03_SV_RD_8bit_RGB_50cm_Sneekermeer_lzw.tif / • tile-170000-550000\20220305_110323_SV1-03_SV_RD_8bit_RGB_50cm_Slotermeer_lzw.tif / • tile-170000-550000\20220305_114830_SV1-02_SV_RD_8bit_RGB_50cm_Sneek_lzw.tif / • tile-170000-550000\20220305_114831_SV1-02_SV_RD_8bit_RGB_50cm_Heeg_lzw.tif / • tile-210000-590000\20220303_101759_SV1-01_SV_RD_8bit_RGB_50cm_Waddenzee_lzw.tif / • tile-210000-590000\20220303_101800_SV1-01_SV_RD_8bit_RGB_50cm_Grijpskerk_lzw.tif / • tile-220000-550000\20220309_111332_SV1-04_SV_RD_8bit_RGB_50cm_Hoogersmilde_lzw.tif / • tile-220000-550000\20220309_111330_SV1-04_SV_RD_8bit_RGB_50cm_Norg_lzw.tif / • tile-220000-550000\20220325_105546_SV1-03_SV_RD_8bit_RGB_50cm_Veenhuizen_lzw.tif / • tile-200000-510000\20220325_105554_SV1-03_SV_RD_8bit_RGB_50cm_Rouveen_lzw.tif / • tile-200000-510000\20220303_101811_SV1-01_SV_RD_8bit_RGB_50cm_Genemuiden_lzw.tif / • tile-200000-540000\20220325_105550_SV1-03_SV_RD_8bit_RGB_50cm_Vledder_lzw.tif / • tile-200000-540000\20220303_101806_SV1-01_SV_RD_8bit_RGB_50cm_Oldeberkoop_lzw.tif / • tile-200000-540000\20220303_101807_SV1-01_SV_RD_8bit_RGB_50cm_Steenwijk_lzw.tif / • tile-180000-390000\20220309_111353_SV1-04_SV_RD_8bit_RGB_50cm_Volkel_lzw.tif / • tile-180000-390000\20220304_105222_SV1-04_SV_RD_8bit_RGB_50cm_Venray_lzw.tif / • tile-180000-390000\20220313_112608_SV1-02_SV_RD_8bit_RGB_50cm_Westerbeek_lzw.tif / • tile-180000-390000\20220313_112607_SV1-02_SV_RD_8bit_RGB_50cm_Oploo_lzw.tif / • tile-190000-560000\20210331_105732_SV1-03_SV_RD_8bit_RGB_50cm_Gorredijk_lzw.tif / • tile-190000-560000\20220311_111047_SV1-03_SV_RD_8bit_RGB_50cm_Burgum_lzw.tif / • tile-190000-560000\20220311_111049_SV1-03_SV_RD_8bit_RGB_50cm_Akkrum_lzw.tif / • tile-230000-440000\20220310_101046_SV1-01_SV_RD_8bit_RGB_50cm_Groenlo_lzw.tif / • tile-230000-440000\20220309_102522_SV1-01_SV_RD_8bit_RGB_50cm_Lichtenvoorde_lzw.tif / • tile-230000-440000\20220306_104908_SV1-03_SV_RD_8bit_RGB_50cm_Ruurlo_lzw.tif / • tile-210000-530000\20220325_105550_SV1-03_SV_RD_8bit_RGB_50cm_Vledder_lzw.tif / • tile-210000-530000\20220309_111335_SV1-04_SV_RD_8bit_RGB_50cm_Ruinen_lzw.tif / • tile-210000-530000\20220309_111334_SV1-04_SV_RD_8bit_RGB_50cm_Dwingeloo_lzw.tif / • tile-210000-530000\20220325_105552_SV1-03_SV_RD_8bit_RGB_50cm_Meppel_lzw.tif / • tile-260000-540000\20220309_102506_SV1-01_SV_RD_8bit_RGB_50cm_Musselkanaal_lzw.tif / • tile-260000-540000\20220309_102508_SV1-01_SV_RD_8bit_RGB_50cm_Emmen_lzw.tif / • tile-260000-540000\20220310_105858_SV1-04_SV_RD_8bit_RGB_50cm_Vlagtwedde_lzw.tif / • tile-260000-540000\20220310_105900_SV1-04_SV_RD_8bit_RGB_50cm_EmmerCompascuum_lzw.tif / • tile-200000-590000\20220318_110323_SV1-03_SV_RD_8bit_RGB_50cm_Kollum_lzw.tif / • tile-200000-590000\20220318_110322_SV1-03_SV_RD_8bit_RGB_50cm_Lauwersoog_lzw.tif / • tile-200000-590000\20220311_111044_SV1-03_SV_RD_8bit_RGB_50cm_Wierum_lzw.tif / • tile-200000-590000\20220311_111045_SV1-03_SV_RD_8bit_RGB_50cm_Zwaagwesteinde_lzw.tif / • tile-200000-380000\20220322_102340_SV1-01_SV_RD_8bit_RGB_50cm_Lottum_lzw.tif / • tile-200000-380000\20220316_101736_SV1-01_SV_RD_8bit_RGB_50cm_Horst_lzw.tif / • tile-200000-380000\20220316_101737_SV1-01_SV_RD_8bit_RGB_50cm_Sevenum_lzw.tif / • tile-200000-380000\20220322_102338_SV1-01_SV_RD_8bit_RGB_50cm_Arcen_lzw.tif / • tile-110000-560000\20220319_113129_SV1-02_SV_RD_8bit_RGB_50cm_Texel_lzw.tif / • tile-110000-560000\20220302_112054_SV1-04_SV_RD_8bit_RGB_50cm_Texel_lzw.tif / • tile-180000-520000\20220306_113347_SV1-02_SV_RD_8bit_RGB_50cm_Marknesse_lzw.tif / • tile-180000-520000\20220306_113349_SV1-02_SV_RD_8bit_RGB_50cm_Ens_lzw.tif / • tile-180000-520000\20220311_111054_SV1-03_SV_RD_8bit_RGB_50cm_Emmeloord_lzw.tif / • tile-120000-440000\20220305_114848_SV1-02_SV_RD_8bit_RGB_50cm_Vianen_lzw.tif / • tile-120000-440000\20220304_111803_SV1-03_SV_RD_8bit_RGB_50cm_Montfoort_lzw.tif / • tile-120000-440000\20220304_111805_SV1-03_SV_RD_8bit_RGB_50cm_Schoonhoven_lzw.tif / • tile-240000-590000\20210417_103620_SV1-01_SV_RD_8bit_RGB_50cm_Loppersum_lzw.tif / • tile-240000-590000\20210417_103622_SV1-01_SV_RD_8bit_RGB_50cm_Loppersum_lzw.tif / • tile-240000-590000\20210628_110942_SV1-03_SV_RD_8bit_RGB_50cm_Middelstum_lzw.tif / • tile-170000-490000\20220311_111100_SV1-03_SV_RD_8bit_RGB_50cm_Harderwijk_lzw.tif / • tile-170000-490000\20220306_113351_SV1-02_SV_RD_8bit_RGB_50cm_Dronten_lzw.tif / • tile-170000-490000\20220306_113352_SV1-02_SV_RD_8bit_RGB_50cm_Veluwemeer_lzw.tif / • tile-170000-490000\20220311_111058_SV1-03_SV_RD_8bit_RGB_50cm_Swifterbant_lzw.tif / • tile-210000-570000\20220303_101804_SV1-01_SV_RD_8bit_RGB_50cm_Donkerbroek_lzw.tif / • tile-210000-570000\20220325_105545_SV1-03_SV_RD_8bit_RGB_50cm_Leek_lzw.tif / • tile-210000-570000\20220303_101802_SV1-01_SV_RD_8bit_RGB_50cm_Surhuisterveen_lzw.tif / • tile-180000-460000\20220303_101820_SV1-01_SV_RD_8bit_RGB_50cm_HogeVeluwe_lzw.tif / • tile-180000-460000\20220303_101818_SV1-01_SV_RD_8bit_RGB_50cm_Veluwe_lzw.tif / • tile-180000-460000\20220318_110341_SV1-03_SV_RD_8bit_RGB_50cm_Stroe_lzw.tif / • tile-180000-550000\20220305_110321_SV1-03_SV_RD_8bit_RGB_50cm_Sneekermeer_lzw.tif / • tile-180000-550000\20220311_111051_SV1-03_SV_RD_8bit_RGB_50cm_Joure_lzw.tif / • tile-180000-550000\20220305_110323_SV1-03_SV_RD_8bit_RGB_50cm_Slotermeer_lzw.tif / • tile-180000-550000\20220311_111049_SV1-03_SV_RD_8bit_RGB_50cm_Akkrum_lzw.tif / • tile-150000-480000\20220305_110332_SV1-03_SV_RD_8bit_RGB_50cm_Zeewolde_lzw.tif / • tile-150000-480000\20220305_110334_SV1-03_SV_RD_8bit_RGB_50cm_Zeewolde_lzw.tif / • tile-150000-480000\20220305_114840_SV1-02_SV_RD_8bit_RGB_50cm_Oostvaardersplassen_lzw.tif / • tile-150000-480000\20220305_114842_SV1-02_SV_RD_8bit_RGB_50cm_Huizen_lzw.tif / • tile-190000-400000\20220304_105220_SV1-04_SV_RD_8bit_RGB_50cm_Boxmeer_lzw.tif / • tile-190000-400000\20220309_111353_SV1-04_SV_RD_8bit_RGB_50cm_Volkel_lzw.tif / • tile-180000-360000\20220313_112612_SV1-02_SV_RD_8bit_RGB_50cm_Weert_lzw.tif / • tile-180000-360000\20220515_105137_SV1-03_SV_RD_8bit_RGB_50cm_Hunsel_lzw.tif / • tile-180000-360000\20220515_105135_SV1-03_SV_RD_8bit_RGB_50cm_Meijel_lzw.tif / • tile-190000-380000\20220316_101736_SV1-01_SV_RD_8bit_RGB_50cm_Horst_lzw.tif / • tile-190000-380000\20220304_105222_SV1-04_SV_RD_8bit_RGB_50cm_Venray_lzw.tif / • tile-190000-380000\20220304_105224_SV1-04_SV_RD_8bit_RGB_50cm_Meijel_lzw.tif / • tile-190000-380000\20220316_101737_SV1-01_SV_RD_8bit_RGB_50cm_Sevenum_lzw.tif / • tile-190000-390000\20220304_105220_SV1-04_SV_RD_8bit_RGB_50cm_Boxmeer_lzw.tif / • tile-190000-390000\20220304_105222_SV1-04_SV_RD_8bit_RGB_50cm_Venray_lzw.tif / • tile-190000-390000\20220316_101736_SV1-01_SV_RD_8bit_RGB_50cm_Horst_lzw.tif / • tile-110000-440000\20220304_111805_SV1-03_SV_RD_8bit_RGB_50cm_Schoonhoven_lzw.tif / • tile-110000-440000\20220303_110647_SV1-04_SV_RD_8bit_RGB_50cm_Bodegraven_lzw.tif / • tile-110000-440000\20220303_110649_SV1-04_SV_RD_8bit_RGB_50cm_Moordrecht_lzw.tif / • tile-150000-490000\20220305_110330_SV1-03_SV_RD_8bit_RGB_50cm_Lelystad_lzw.tif / • tile-150000-490000\20220305_110332_SV1-03_SV_RD_8bit_RGB_50cm_Zeewolde_lzw.tif / • tile-150000-490000\20220305_114839_SV1-02_SV_RD_8bit_RGB_50cm_Oostvaardersplassen_lzw.tif / • tile-150000-490000\20220305_114840_SV1-02_SV_RD_8bit_RGB_50cm_Oostvaardersplassen_lzw.tif / • tile-140000-590000\20220303_110626_SV1-04_SV_RD_8bit_RGB_50cm_Terschelling_lzw.tif / • tile-140000-590000\20220308_103936_SV1-01_SV_RD_8bit_RGB_50cm_Terschelling_lzw.tif / • tile-170000-430000\20220303_101822_SV1-01_SV_RD_8bit_RGB_50cm_Oosterbeek_lzw.tif / • tile-170000-430000\20220303_101823_SV1-01_SV_RD_8bit_RGB_50cm_Beuningen_lzw.tif / • tile-170000-430000\20220318_110345_SV1-03_SV_RD_8bit_RGB_50cm_Rhenen_lzw.tif / • tile-170000-430000\20220318_110347_SV1-03_SV_RD_8bit_RGB_50cm_Maasbommel_lzw.tif / • tile-80000-460000\20210423_104948_SV1-01_SV_RD_8bit_RGB_50cm_KatwijkAanZee_lzw.tif / • tile-80000-460000\20210423_104950_SV1-01_SV_RD_8bit_RGB_50cm_DenHaag_lzw.tif / • tile-80000-460000\20210426_112150_SV1-03_SV_RD_8bit_RGB_50cm_Zoetermeer_lzw.tif / • tile-110000-450000\20220303_110645_SV1-04_SV_RD_8bit_RGB_50cm_Nieuwkoop_lzw.tif / • tile-110000-450000\20220303_110647_SV1-04_SV_RD_8bit_RGB_50cm_Bodegraven_lzw.tif / • tile-110000-450000\20220304_111803_SV1-03_SV_RD_8bit_RGB_50cm_Montfoort_lzw.tif / • tile-20000-370000\20210302_111348_SV1-03_SV_RD_8bit_RGB_50cm_IJzendijke_lzw.tif / • tile-20000-370000\20210329_112454_SV1-03_SV_RD_8bit_RGB_50cm_Breskens_lzw.tif / • tile-20000-370000\20210329_112456_SV1-03_SV_RD_8bit_RGB_50cm_Oostburg_lzw.tif / • tile-50000-420000\20220317_111822_SV1-03_SV_RD_8bit_RGB_50cm_Ouddorp_lzw.tif / • tile-50000-420000\20220317_111823_SV1-03_SV_RD_8bit_RGB_50cm_Brouwersdam_lzw.tif / • tile-50000-420000\20220324_111044_SV1-03_SV_RD_8bit_RGB_50cm_Rockanje_lzw.tif / • tile-50000-420000\20220324_111046_SV1-03_SV_RD_8bit_RGB_50cm_Grevelingen_lzw.tif / • tile-90000-480000\20220302_112105_SV1-04_SV_RD_8bit_RGB_50cm_Zandvoort_lzw.tif / • tile-90000-480000\20220302_112107_SV1-04_SV_RD_8bit_RGB_50cm_Noordwijkerhout_lzw.tif / • tile-100000-510000\20220302_112059_SV1-04_SV_RD_8bit_RGB_50cm_Schoorl_lzw.tif / • tile-100000-510000\20220302_112101_SV1-04_SV_RD_8bit_RGB_50cm_EgmondAanZee_lzw.tif / • tile-110000-410000\20220304_111809_SV1-03_SV_RD_8bit_RGB_50cm_Biesbosch_lzw.tif / • tile-110000-410000\20220304_111810_SV1-03_SV_RD_8bit_RGB_50cm_Prinsenbeek_lzw.tif / • tile-110000-410000\20220305_114851_SV1-02_SV_RD_8bit_RGB_50cm_Capelle_lzw.tif / • tile-110000-410000\20220305_114853_SV1-02_SV_RD_8bit_RGB_50cm_Dongen_lzw.tif / • tile-110000-460000\20210908_104923_SV1-01_SV_RD_8bit_RGB_50cm_Nieuwkoop_lzw.tif / • tile-110000-460000\20210908_104924_SV1-01_SV_RD_8bit_RGB_50cm_Bodegraven_lzw.tif / • tile-140000-380000\20220306_113407_SV1-02_SV_RD_8bit_RGB_50cm_Oirschot_lzw.tif / • tile-140000-380000\20220306_113408_SV1-02_SV_RD_8bit_RGB_50cm_Eersel_lzw.tif / • tile-140000-380000\20220311_111114_SV1-03_SV_RD_8bit_RGB_50cm_Hilvarenbeek_lzw.tif / • tile-140000-380000\20220311_111116_SV1-03_SV_RD_8bit_RGB_50cm_Reusel_lzw.tif / • tile-180000-470000\20210615_105923_SV1-03_SV_RD_8bit_RGB_50cm_Vaassen_lzw.tif / • tile-180000-470000\20210615_105925_SV1-03_SV_RD_8bit_RGB_50cm_Veluwe_lzw.tif / • tile-180000-470000\20210618_110146_SV1-04_SV_RD_8bit_RGB_50cm_Elspeet_lzw.tif / • tile-180000-470000\20210618_110148_SV1-04_SV_RD_8bit_RGB_50cm_Stroe_lzw.tif / • tile-190000-310000\20210303_105956_SV1-03_SV_RD_8bit_RGB_50cm_Valkenburg_lzw.tif / • tile-190000-310000\20210428_105453_SV1-03_SV_RD_8bit_RGB_50cm_Heerlen_lzw.tif / • tile-190000-310000\20210428_105454_SV1-03_SV_RD_8bit_RGB_50cm_Epen_lzw.tif / • tile-230000-520000\20200404_103929_SV1-01_SV_RD_8bit_RGB_50cm_Hoogeveen_lzw.tif / • tile-230000-520000\20200404_103931_SV1-01_SV_RD_8bit_RGB_50cm_Slagharen_lzw.tif / • tile-230000-520000\20200422_110732_SV1-03_SV_RD_8bit_RGB_50cm_Geesbrug_lzw.tif / • tile-230000-520000\20200422_110734_SV1-03_SV_RD_8bit_RGB_50cm_Hardenberg_lzw.tif

Bookmark: Process
Creator
    GEOMTYPE = Geometry Object
    NUM = 1
    CREATED -> FeatureReader [INITIATOR]
    CREATED -> FeatureReader_4 [INITIATOR]
Note: read sample tiles
FeatureReader
    ATTRIBUTES = tiles_copy,"id,landscape,filename_10k,overlap_landscape,overlap_non_urban,overlap_total,shape_leng,split,fid"
    ATTR_ACCUM_MODE = Only Use Result
    COMBINE_GEOM = Use Result
    DATASET = $(sample_file)
    FEATURETYPES = tiles_copy
    FORMAT = OGCGEOPACKAGE
    GEOMETRY_TYPES = tiles_copy,""",fme_area"""
    INTERACT = NONE
    OGCGEOPACKAGE_ENCODE_FEATURE_TYPE_AND_ATTR_NAMES = YES
    OGCGEOPACKAGE_ENFORCE_FOREIGN_KEY_INTEGRITY = YES
    OGCGEOPACKAGE_EXPOSE_PRIMARY_KEY_ATTRIBUTE = YES
    OGCGEOPACKAGE_OPEN_SINGLE_RASTER_AS_SUBDATASET = YES
    OGCGEOPACKAGE_QUERY_FEATURE_TYPES_FOR_MERGE_FILTERS = Yes
    OGCGEOPACKAGE_READER_REPLACE_INVALID_CHARS = YES
    OGCGEOPACKAGE_READ_BOOLEANS_AS_YES_NO = YES
    OGCGEOPACKAGE_READ_NULLS = YES
    OGCGEOPACKAGE_USE_SEARCH_ENVELOPE = NO
    OUTPUT_FEATURES_DISPLAY = Schema and Data Features
    tiles_copy -> TestFilter
TestFilter
    DEFAULT_VALUE = <UNFILTERED>
    PASSED_TEST_GROUP_OUTPUT = FIRST
    TEST_LIST = "BOOL_OP,OR,COMPOSITE_TEST,""""""1"""""",TEST_CLAUSE,TEST @Value(filename_10k) = $(filename)",@Value(filename_10k) = __filename_
    @Value(filename_10k) = __filename_ -> StringReplacer
StringReplacer
    CASE = NO
    FIND_TEXT = .tif
    NO_MATCH = _FME_NO_OP_
    REGEXP = NO
    SRC_ATTRS = filename_10k
    -> CoordinateExtractor
CoordinateExtractor
    LIST_NAME = _indices
    MODE = All Coordinates
    -> FeatureReader_3 [INITIATOR]
Note: Set image dir
FeatureReader_3
    ATTRIBUTES = PATH,"path_unix,path_windows,path_rootname,path_filename,path_extension,path_directory_unix,path_directory_windows,path_type,fme_geometry{0}"
    ATTR_ACCUM_MODE = Merge Initiator and Result
    ATTR_CONFLICT_RES = Use Result
    ATTR_IGNORE_NULLS = No
    COMBINE_GEOM = Use Result
    DATASET = $(input_dir)
    FEATURETYPES = PATH
    FORMAT = PATH
    OUTPUT_FEATURES_DISPLAY = Schema and Data Features
    PATH_GLOB_PATTERN = *
    PATH_HIDDEN_FILES = INCLUDE
    PATH_NO_EMPTY_PROPERTIES = YES
    PATH_OFFSET_DATETIME = yes
    PATH_RECURSE_DIRECTORIES = YES
    PATH_RETRIEVE_FILE_PROPERTIES = NO
    PATH_TYPE = ANY
    PATH_USE_NON_STRING_ATTR = yes
    PATH -> TestFilter_2
TestFilter_2
    DEFAULT_VALUE = <UNFILTERED>
    PASSED_TEST_GROUP_OUTPUT = FIRST
    TEST_LIST:
      "BOOL_OP,AND,COMPOSITE_TEST,""""""1 AND 2"""""",TEST_CLAUSE,CASE_INSENSITIVE_TEST @Value(path_windows) CONTAINS @Value(filename_10k)
      CASE_INSENSITIVE_TEST @Value(path_type) = file",@Value(path_windows) CONTAINS @Value(filename_10k)
    @Value(path_windows) CONTAINS @Value(filename_10k) -> FeatureReader_2 [INITIATOR]
Note: Read images
FeatureReader_2
    ATTR_ACCUM_MODE = Merge Initiator and Result
    ATTR_CONFLICT_RES = Use Result
    ATTR_IGNORE_NULLS = No
    COMBINE_GEOM = Use Result
    DATASET = @Value(path_windows)
    FEATURETYPES = GEOTIFF
    FORMAT = GEOTIFF
    GEOTIFF_APPLY_GCPS = NO
    GEOTIFF_FEATURE_TYPE_NAME = FORMAT_NAME
    GEOTIFF_GEOTIFF_EXPOSE_FORMAT_ATTRS = fme_basename,char(50)
    GEOTIFF_IGNORE_RASTER_TYPE_KEY = No
    GEOTIFF_PREFER_FILE_CS_UNITS = Yes
    GEOTIFF_READER_META_ATTRIBUTES = fme_dataset fme_basename
    GEOTIFF_READ_OFFSETS_IN_CS_UNITS = No
    GEOTIFF_USE_SEARCH_ENVELOPE = NO
    INTERACT = ENVELOPE_INTERSECTS
    OUTPUT_FEATURES_DISPLAY = Schema and Data Features
    <OTHER> -> AttributeManager
AttributeManager
    ATTR_TABLE:
      REMOVE id
      REMOVE path_unix
      REMOVE path_windows
      REMOVE path_rootname
      REMOVE path_filename
      REMOVE path_extension
      REMOVE path_directory_unix
      REMOVE path_directory_windows
      REMOVE path_type
      REMOVE fme_geometry{0}
      REMOVE fme_geometry{}
    USER_EXPOSED_ATTRIBUTES = path_filesize,path_accessed_date,path_ownername,path_readonly,path_modified_date,path_created_date
    -> RasterBandNodataSetter
RasterBandNodataSetter
    NODATA_VALUE = 0
    REPLACE_CELL_VALUES = Yes
    -> RasterMosaicker
RasterMosaicker
    ACCUM_ATTRS_NAME = Use Attributes From One Feature
    GROUP_BY = filename_10k
    INTERPOLATION_TYPE_NAME = Nearest Neighbor
    MERGE_PALETTES_NAME = Yes
    OVERLAPPING_VALUES = min
    SNAPPING_TYPE_NAME = Resample
    -> RasterGeoreferencer
RasterGeoreferencer
    POINTANDANGLE_OR_EXTENTS = Extents
    X_LL_COORD = @Value(_indices{0}.x)
    X_LR_COORD = @Value(_indices{3}.x)
    X_UL_COORD = @Value(_indices{1}.x)
    X_UR_COORD = @Value(_indices{2}.x)
    Y_LL_COORD = @Value(_indices{0}.y)
    Y_LR_COORD = @Value(_indices{3}.y)
    Y_UL_COORD = @Value(_indices{1}.y)
    Y_UR_COORD = @Value(_indices{2}.y)
    -> StringReplacer_4
StringReplacer_4
    CASE = NO
    FIND_TEXT = .tif
    NO_MATCH = _FME_NO_OP_
    REGEXP = NO
    SRC_ATTRS = filename_10k
    -> RasterResampler
RasterResampler
    COLUMNS = 20000
    INTERPOLATION_TYPE_NAME = Nearest Neighbor
    ROWCOL_OR_CELLSIZE = RowsColumns
    ROWS = 20000
    RESAMPLED -> Clipper_2 [CANDIDATE]
Note: Read country border
FeatureReader_4
    ATTRIBUTES = gemeenten,"code,gemeentenaam,fid",landsgrens,"code,landsnaam,fid",provincies,"provincienaam,fid"
    ATTR_ACCUM_MODE = Only Use Result
    COMBINE_GEOM = Use Result
    DATASET = $(country_border)
    FEATURETYPES = landsgrens
    FORMAT = OGCGEOPACKAGE
    GEOMETRY_TYPES = gemeenten,""",fme_area""",landsgrens,""",fme_area""",provincies,""",fme_area"""
    INTERACT = NONE
    OGCGEOPACKAGE_ENCODE_FEATURE_TYPE_AND_ATTR_NAMES = YES
    OGCGEOPACKAGE_ENFORCE_FOREIGN_KEY_INTEGRITY = YES
    OGCGEOPACKAGE_EXPOSE_PRIMARY_KEY_ATTRIBUTE = YES
    OGCGEOPACKAGE_OPEN_SINGLE_RASTER_AS_SUBDATASET = YES
    OGCGEOPACKAGE_QUERY_FEATURE_TYPES_FOR_MERGE_FILTERS = Yes
    OGCGEOPACKAGE_READER_REPLACE_INVALID_CHARS = YES
    OGCGEOPACKAGE_READ_BOOLEANS_AS_YES_NO = YES
    OGCGEOPACKAGE_READ_NULLS = YES
    OGCGEOPACKAGE_USE_SEARCH_ENVELOPE = NO
    OUTPUT_FEATURES_DISPLAY = Schema and Data Features
    landsgrens -> Clipper_2 [CLIPPER]
Clipper_2
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = YES
    RASTER_CELL_MODE = CENTER
    Z_VAL_SOURCE = CANDIDATE
    INSIDE -> RasterBandNodataSetter_2
RasterBandNodataSetter_2
    NODATA_VALUE = 0
    REPLACE_CELL_VALUES = Yes
    -> StringReplacer_2
StringReplacer_2
    CASE = NO
    FIND_TEXT = .tif
    NO_MATCH = _FME_NO_OP_
    REGEXP = NO
    SRC_ATTRS = filename_10k
    -> FeatureWriter [Resampled]
Note: Set output dir
FeatureWriter
    DATASET = $(output_dir)
    DATASET_ATTR = _dataset
    FEATURE_TYPE_LIST_ATTR = _feature_types
    FORMAT = GEOTIFF
    GEOTIFF_COORDINATE_SYSTEM_GRANULARITY = FEATURE
    GEOTIFF_DESTINATION_DATASETTYPE_VALIDATION = Yes
    GEOTIFF_FORMAT_ATTRIBUTES_OVERRIDE_FEATURE_TYPE_PARAMETERS = Yes
    GEOTIFF_IGNORE_RASTER_TYPE_KEY = No
    GEOTIFF_WRITE_ESRI_COMPATIBLE_COORDSYS = No
    GEOTIFF_WRITE_GEOGRAPHIC_COORDSYS_AS_EPSG_CODE = Yes
    GEOTIFF_WRITE_GEOGRAPHIC_KEYS_FOR_PROJECTED_COORDSYS = Yes
    GEOTIFF_WRITE_OFFSETS_IN_CS_UNITS = Yes
    GEOTIFF_WRITE_PROJECTED_COORDSYS_AS_EPSG_CODE = Yes
    TOTAL_FEATURES_WRITTEN_ATTR = _total_features_written
